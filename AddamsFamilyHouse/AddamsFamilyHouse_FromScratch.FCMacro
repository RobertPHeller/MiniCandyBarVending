#*****************************************************************************
#
#  System        : 
#  Module        : 
#  Object Name   : $RCSfile$
#  Revision      : $Revision$
#  Date          : $Date$
#  Author        : $Author$
#  Created By    : Robert Heller
#  Created       : Thu Jun 5 14:31:17 2025
#  Last Modified : <250711.1525>
#
#  Description	
#
#  Notes
#
#  History
#	
#*****************************************************************************
#
#    Copyright (C) 2025  Robert Heller D/B/A Deepwoods Software
#			51 Locke Hill Road
#			Wendell, MA 01379-9728
#
#    This program is free software; you can redistribute it and/or modify
#    it under the terms of the GNU General Public License as published by
#    the Free Software Foundation; either version 2 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program; if not, write to the Free Software
#    Foundation, Inc., 675 Mass Ave, Cambridge, MA 02139, USA.
#
# 
#
#*****************************************************************************


import FreeCAD as App
import Part, TechDraw, Mesh, MeshPart, TechDrawGui
from FreeCAD import Base

import math

import os
import sys
sys.path.append(os.path.dirname(__file__))

import time
from PySide.QtCore import QCoreApplication, QEventLoop, QTimer
def execute(loop, ms):
    timer = QTimer()
    timer.setSingleShot(True)
    
    timer.timeout.connect(loop.quit)
    timer.start(ms)
    loop.exec_()

def sleep(ms):
    if not QCoreApplication.instance():
        app = QCoreApplication([])
        execute(app, ms)
    else:
        loop = QEventLoop()
        execute(loop, ms)

from abc import ABCMeta, abstractmethod, abstractproperty

class BirchPanel(metaclass=ABCMeta):
    @staticmethod
    def FitPanel(page,lastX,lastY,lengthX,lengthY,deltaY,minX,minY,maxX,maxY):
        views = page.getAllViews()
        currentX = lastX
        currentY = lastY
        rotation = 0
        if (lengthY > 2*deltaY and lengthX < deltaY) or \
            lengthY > lengthX*2:
            temp = lengthX
            lengthX = lengthY
            lengthY = temp
            rotation = 90
        if currentX+lengthX < maxX and \
           currentY+lengthY < maxY:
            #print("*** BirchPanel.FitPanel(A): deltaY = ",deltaY,", lengthY = ",lengthY)
            deltaY = max(deltaY,lengthY+10)
            return (True, currentX, currentY, lengthX, lengthY, deltaY, rotation)
        elif currentX+lengthX > maxX and \
           currentY+lengthY+deltaY < maxY and \
           minX+lengthX < maxX:
            currentX = minX
            currentY += deltaY
            return (True, currentX, currentY, lengthX, lengthY+10, deltaY, rotation)
        elif currentY+lengthY > maxY and \
             currentY+lengthX < maxY and \
             currentX+lengthY < maxX:
            temp = lengthX
            lengthX = lengthY
            lengthY = temp
            if rotation == 0:
                rotation = 90
            else:
                rotation = 0
            #print("*** BirchPanel.FitPanel(B): deltaY = ",deltaY,", lengthY = ",lengthY)
            deltaY = max(deltaY,lengthY+10)
            return (True, currentX, currentY, lengthX, lengthY, deltaY, rotation)
        elif currentY+deltaY+lengthX < maxY and \
             minX+lengthY < maxX:
            temp = lengthX
            lengthX = lengthY
            lengthY = temp
            if rotation == 0:
                rotation = 90
            else:
                rotation = 0
            currentX = minX
            currentY += deltaY
            return (True, currentX, currentY, lengthX, lengthY+10, deltaY, rotation)
        else:
            return (False, lastX, lastY, lengthX, lengthY, deltaY, rotation)
    @staticmethod
    def Thickness():
        return .125 * 25.4
    @property
    def FingerWidth(self):
        return .5 * 25.4
    @property
    def Color(self):
        return (.8,.8,.8)
    @abstractmethod
    def PanelPage(self,techDoc,page,lastX,lastY,deltaY,*,minX=50,minY=50,
                                             maxX=(24*25.4)-50,
                                             maxY=(16*25.4)-50):
        pass

class LargeArchWindow(BirchPanel):
    # -263.86346435546875,  .8360995054244995  -- -241.0014190673828 , 0.8360995054244995
    # -263.86346435546875 , 50.67988586425781                  50.67988586425781
    #       -252.43243408203125 , 66.17835235595703
    __archMinorRadius = (-241.0014190673828) - (-252.43243408203125)
    __archMajorRadius = 66.17835235595703-50.67988586425781
    __bottomRectHeight = 50.67988586425781-.8360995054244995
    __bottomRectWidth = (-241.0014190673828) - (-263.86346435546875)
    __TrimThickness = .75
    __LEDMountDepth = 12.5
    __TrimWidth = 1.5
    __trimColor=(139/255, 35/255, 35/255)
    __LEDMountColor=(0.0, 0.0, 0.0)
    def PanelPage(self,techDoc,page,lastX,lastY,deltaY,*,minX=50,minY=50,
                                             maxX=(24*25.4)-50,
                                             maxY=(16*25.4)-50):
        return (False, -1, -1, deltaY)
    @classmethod
    def Trim3DPrint(cls,*,doc=None,filename='LargeArchWindowTrim.stl'):
        archOrig = Base.Vector(cls.__archMinorRadius,
                               cls.__bottomRectHeight,0)
        archMajor = archOrig.add(Base.Vector(0,cls.__archMajorRadius,0))
        archOMajor = archMajor.add(Base.Vector(0,cls.__TrimWidth,0))
        archMinor = archOrig.add(Base.Vector(-cls.__archMinorRadius,0,0))
        archOMinor = archMinor.add(Base.Vector(-cls.__TrimWidth,0,0))
        extrudeTrim = Base.Vector(0,0,cls.__TrimThickness)
        baseOOffset = Base.Vector(-cls.__TrimWidth,-cls.__TrimWidth,0)
        archEllipse=Part.Ellipse(archOMajor,archOMinor,archOrig)
        archWire = Part.Wire(archEllipse.toShape())
        archFace = Part.Face(archWire)
        arch     = archFace.extrude(extrudeTrim)
        base     = Part.makePlane(cls.__bottomRectWidth+(cls.__TrimWidth*2),
                                  cls.__bottomRectHeight,
                                  baseOOffset).extrude(extrudeTrim)
        windowTrim = base.fuse(arch)
        archEllipse=Part.Ellipse(archMajor,archMinor,archOrig)
        archWire = Part.Wire(archEllipse.toShape()) 
        archFace = Part.Face(archWire)
        arch     = archFace.extrude(extrudeTrim)
        base     = Part.makePlane(cls.__bottomRectWidth,
                                  cls.__bottomRectHeight
                                  ).extrude(extrudeTrim)
        windowTrim = windowTrim.cut(base.fuse(arch)) 
        if doc==None:
            if "WindowTrim" in App.listDocuments().keys():
                App.closeDocument("WindowTrim")
            doc=App.newDocument('WindowTrim')
        obj = doc.addObject("Part::Feature","WindowTrim")
        obj.Shape = windowTrim
        objs = list()
        objs.append(obj)
        Mesh.export(objs,filename)
    @classmethod
    def LEDMount3DPrint(cls,*,doc=None,filename='LargeArchWindowLEDMount.stl'):
        archOrig = Base.Vector(cls.__archMinorRadius,
                               cls.__bottomRectHeight,0)
        archMajor = archOrig.add(Base.Vector(0,cls.__archMajorRadius,0))
        archOMajor = archMajor.add(Base.Vector(0,cls.__TrimWidth,0))
        archMinor = archOrig.add(Base.Vector(-cls.__archMinorRadius,0,0))
        archOMinor = archMinor.add(Base.Vector(-cls.__TrimWidth,0,0))
        extrudeLEDMount = Base.Vector(0,0,cls.__LEDMountDepth)
        baseOOffset = Base.Vector(-cls.__TrimWidth,-cls.__TrimWidth,0)
        archEllipse=Part.Ellipse(archOMajor,archOMinor,archOrig)
        archWire = Part.Wire(archEllipse.toShape())
        archFace = Part.Face(archWire)
        arch     = archFace.extrude(extrudeLEDMount)
        base     = Part.makePlane(cls.__bottomRectWidth+(cls.__TrimWidth*2),
                                  cls.__bottomRectHeight,
                                  baseOOffset).extrude(extrudeLEDMount)
        windowLEDMount = base.fuse(arch)
        archEllipse=Part.Ellipse(archMajor,archMinor,archOrig)
        archWire = Part.Wire(archEllipse.toShape()) 
        archFace = Part.Face(archWire)
        arch     = archFace.extrude(extrudeLEDMount)
        base     = Part.makePlane(cls.__bottomRectWidth,
                                  cls.__bottomRectHeight,
                                  ).extrude(extrudeLEDMount)
        windowLEDMount = windowLEDMount.cut(base.fuse(arch)) 
        if doc==None:
            if "WindowLEDMount" in App.listDocuments().keys():
                App.closeDocument("WindowLEDMount")
            doc=App.newDocument('WindowLEDMount')
        obj = doc.addObject("Part::Feature","WindowLEDMount")
        obj.Shape = windowLEDMount
        objs = list()
        objs.append(obj)
        Mesh.export(objs,filename)
    def __init__(self,origin,side='Front',name="window"):
        self.name = name
        if not isinstance(origin,Base.Vector):
            raise RuntimeError("origin is not a Vector!")
        self.origin = origin
        if side == 'Front':
            archOrig = origin.add(Base.Vector(self.__archMinorRadius,0,
                                              self.__bottomRectHeight))
            archMajor = archOrig.add(Base.Vector(0,0,self.__archMajorRadius))
            archOMajor = archMajor.add(Base.Vector(0,0,self.__TrimWidth))
            archMinor = archOrig.add(Base.Vector(-self.__archMinorRadius,0,0))
            archOMinor = archMinor.add(Base.Vector(-self.__TrimWidth,0,0))
            extrude = Base.Vector(0,BirchPanel.Thickness(),0)
            trimOffset = Base.Vector(0,0,0)
            extrudeTrim = Base.Vector(0,-self.__TrimThickness,0)
            LEDMountOffset = extrude
            extrudeLEDMount = Base.Vector(0,self.__LEDMountDepth,0)
            
            #print("*** LargeArchWindow.__init__(): archOrig is ",archOrig)
            #print("*** LargeArchWindow.__init__(): archMajor is ",archMajor)
            #print("*** LargeArchWindow.__init__(): archMinor is ",archMinor)
            baseOffset = Base.Vector(0,0,0)
            baseOOffset = baseOffset.add(Base.Vector(-self.__TrimWidth,0,
                                                     -self.__TrimWidth))
            baseNorm = Base.Vector(0,1,0)
        elif side == 'Left':
            archOrig = origin.add(Base.Vector(0,
                                              -self.__archMinorRadius,
                                              self.__bottomRectHeight))
            archMajor = archOrig.add(Base.Vector(0,0,self.__archMajorRadius))
            archOMajor = archMajor.add(Base.Vector(0,0,self.__TrimWidth))
            archMinor = archOrig.add(Base.Vector(0,self.__archMinorRadius,0))
            archOMinor = archMinor.add(Base.Vector(0,self.__TrimWidth,0))
            extrude = Base.Vector(BirchPanel.Thickness(),0,0)
            trimOffset = Base.Vector(0,0,0)
            extrudeTrim = Base.Vector(-self.__TrimThickness,0,0)
            LEDMountOffset = extrude
            extrudeLEDMount = Base.Vector(self.__LEDMountDepth,0,0)
            baseOffset = Base.Vector(0,0,self.__bottomRectHeight)
            baseOOffset = baseOffset.add(Base.Vector(0,self.__TrimWidth,
                                                     -self.__TrimWidth))
            baseNorm = Base.Vector(-1,0,0)
        elif side == 'Right':
            archOrig = origin.add(Base.Vector(0,
                                              self.__archMinorRadius,
                                              self.__bottomRectHeight))
            archMajor = archOrig.add(Base.Vector(0,0,self.__archMajorRadius))
            archOMajor = archMajor.add(Base.Vector(0,0,self.__TrimWidth))
            archMinor = archOrig.add(Base.Vector(0,self.__archMinorRadius,0))
            archOMinor = archMinor.add(Base.Vector(0,self.__TrimWidth,0))
            extrude = Base.Vector(BirchPanel.Thickness(),0,0)
            trimOffset = extrude
            extrudeTrim = Base.Vector(self.__TrimThickness,0,0)
            LEDMountOffset = Base.Vector(0,0,0)
            extrudeLEDMount = Base.Vector(-self.__LEDMountDepth,0,0)
            baseOffset = Base.Vector(0,self.__bottomRectWidth,0)
            baseOOffset = baseOffset.add(Base.Vector(0,self.__TrimWidth,
                                                     -self.__TrimWidth))
            baseNorm = Base.Vector(1,0,0)
        else:
            raise RuntimeError("unsuported side!")
        archEllipse=Part.Ellipse(archMajor,archMinor,archOrig)
        archWire = Part.Wire(archEllipse.toShape())
        archFace = Part.Face(archWire)
        arch     = archFace.extrude(extrude)
        base     = Part.makePlane(self.__bottomRectHeight,
                                  self.__bottomRectWidth,
                                  origin.add(baseOffset),
                                  baseNorm).extrude(extrude)
        self.windowCutout = base.fuse(arch)
        archEllipse=Part.Ellipse(archOMajor.add(trimOffset),
                                 archOMinor.add(trimOffset),
                                 archOrig.add(trimOffset))
        archWire = Part.Wire(archEllipse.toShape())
        archFace = Part.Face(archWire)
        arch     = archFace.extrude(extrudeTrim)
        base     = Part.makePlane(self.__bottomRectHeight,
                                  self.__bottomRectWidth+(self.__TrimWidth*2),
                                  origin.add(baseOOffset).add(trimOffset),
                                  baseNorm).extrude(extrudeTrim)
        self.windowTrim = base.fuse(arch)
        archEllipse=Part.Ellipse(archMajor.add(trimOffset),
                                 archMinor.add(trimOffset),
                                 archOrig.add(trimOffset))
        archWire = Part.Wire(archEllipse.toShape())
        archFace = Part.Face(archWire)
        arch     = archFace.extrude(extrudeTrim)
        base     = Part.makePlane(self.__bottomRectHeight,
                                  self.__bottomRectWidth,
                                  origin.add(baseOffset).add(trimOffset),
                                  baseNorm).extrude(extrudeTrim)
        self.windowTrim = self.windowTrim.cut(base.fuse(arch))
        archEllipse=Part.Ellipse(archOMajor.add(LEDMountOffset),
                                 archOMinor.add(LEDMountOffset),
                                 archOrig.add(LEDMountOffset))
        archWire = Part.Wire(archEllipse.toShape())
        archFace = Part.Face(archWire)
        arch     = archFace.extrude(extrudeLEDMount)
        base     = Part.makePlane(self.__bottomRectHeight,
                                  self.__bottomRectWidth+(self.__TrimWidth*2),
                                  origin.add(baseOOffset).add(LEDMountOffset),
                                  baseNorm).extrude(extrudeLEDMount)
        self.windowLEDMount = base.fuse(arch)
        archEllipse=Part.Ellipse(archMajor.add(LEDMountOffset),
                                 archMinor.add(LEDMountOffset),
                                 archOrig.add(LEDMountOffset))
        archWire = Part.Wire(archEllipse.toShape())
        archFace = Part.Face(archWire)
        arch     = archFace.extrude(extrudeLEDMount)
        base     = Part.makePlane(self.__bottomRectHeight,
                                  self.__bottomRectWidth,
                                  origin.add(baseOffset).add(LEDMountOffset),
                                  baseNorm).extrude(extrudeLEDMount)
        self.windowLEDMount = self.windowLEDMount.cut(base.fuse(arch))
    def Cut(self,wall):
        return wall.cut(self.windowCutout)
    def show(self,doc=None):
        if doc==None:
            doc = App.activeDocument()
        obj = doc.addObject("Part::Feature",self.name+"_trim")
        obj.Shape = self.windowTrim
        obj.Label=self.name+"_trim"
        obj.ViewObject.ShapeColor=self.__trimColor
        obj = doc.addObject("Part::Feature",self.name+"_LEDMount")
        obj.Shape = self.windowLEDMount
        obj.Label=self.name+"_LEDMount"
        obj.ViewObject.ShapeColor=self.__LEDMountColor

class InstanceIter(metaclass=ABCMeta):
    @classmethod
    def SetIter(cls):
        #print('*** InstanceIter.__iter__(',cls,')')
        try:
            panels = cls.__Panels
        except AttributeError:
            cls.__Panels = set()
        return cls.__Panels.__iter__()
    def __del__(self):
        #print('*** InstanceIter.__del__(',self,')')
        #print('*** InstanceIter.__del__(): self.__class__ is ',self.__class__)
        try:
            panels = self.__class__.__Panels
        except AttributeError:
            self.__class__.__Panels = set()
        self.__class__.__Panels.remove(self)
    def __init__(self):
        #print('*** InstanceIter.__init__(',self,')')
        #print('*** InstanceIter.__init__(): self.__class__ is ',self.__class__)
        try:
            panels = self.__class__.__Panels
        except AttributeError:
            self.__class__.__Panels = set()
        self.__class__.__Panels.add(self)
        #print('*** InstanceIter.__init__(): self.__class__.__Panels is',self.__class__.__Panels)
    @classmethod
    def SortedList(cls):
        return cls.SortSet(cls.__Panels)
    @abstractmethod
    def sortKey(self):
        pass
    @staticmethod
    def __sortkey(item):
        return item.sortKey()
    @classmethod 
    def SortSet(cls,panelSet):
        panelList =  list(panelSet)
        panelList.sort(key=cls.__sortkey)
        return panelList

class WallPanel(BirchPanel,InstanceIter):
    def sortKey(self):
        bbox = self.wall.BoundBox
        a = bbox.ZLength
        b = max(bbox.XLength,bbox.YLength)
        return math.hypot(a,b)
    def __str__(self):
        try:
            result = '<WallPanel name="'+self.name+'"'
            result = result+', origin='+str(self.origin)
            result = result+', side="'+self.side+'">'
            return result
        except BaseException:
            return "<WallPanel>"        
    def __init__(self,name,origin,width,height,*,windows=[],side='Front'):
        super(WallPanel,self).__init__()
        self.name = name
        if not isinstance(origin,Base.Vector):
            raise RuntimeError("origin is not a Vector!")
        self.origin = origin
        self.side = side
        if side == 'Front':
            #print("*** WallPanel(): width = ",width,", height = ",height)
            extrude = Base.Vector(0,BirchPanel.Thickness(),0)
            panel = Part.makePlane(height,width,origin,Base.Vector(0,1,0)).extrude(extrude)
        elif side == 'Left':
            extrude = Base.Vector(-BirchPanel.Thickness(),0,0)
            panel = Part.makePlane(height,width,
                                   origin.add(Base.Vector(BirchPanel.Thickness(),width,height)),
                                   Base.Vector(-1,0,0)).extrude(extrude)
        elif side == 'Right':
            extrude = Base.Vector(BirchPanel.Thickness(),0,0)
            panel = Part.makePlane(height,width,
                                   origin.add(Base.Vector(0,width,0)),
                                   Base.Vector(1,0,0)).extrude(extrude)
        elif side == 'Rear':
             extrude = Base.Vector(0,-BirchPanel.Thickness(),0)
             panel = Part.makePlane(height,
                                    width,
                                    origin.add(Base.Vector(-width,0,height)),
                                    Base.Vector(0,-1,0)).extrude(extrude)
        else:
            raise RuntimeError("unsuported side!")
        self.windows = list()
        for i,org in enumerate(windows):
            w = LargeArchWindow(origin.add(org),side,name+"_window%02d"%(i))
            panel = w.Cut(panel)
            self.windows.append(w)
        self.wall = panel
    def CutXZfingers(self,*,startx=0,endx=0,zoffset=0,yoffset=0):
        x = startx
        ZNorm=Base.Vector(0,0,1)
        panel = self.wall
        while x <= endx:
            panel = panel.cut(Part.makePlane(self.FingerWidth,\
                                             BirchPanel.Thickness(),\
                                             self.origin.add(Base.Vector(x,yoffset,zoffset)),\
                                             ZNorm).extrude(Base.Vector(0,0,BirchPanel.Thickness())))
            x += self.FingerWidth*2
        self.wall = panel
    def CutYZfingers(self,*,starty=0,endy=0,zoffset=0,xoffset=0):
        y = starty
        ZNorm=Base.Vector(0,0,1) 
        panel = self.wall
        while y <= endy:
            panel = panel.cut(Part.makePlane(BirchPanel.Thickness(),\
                                             self.FingerWidth,\
                                             self.origin.add(Base.Vector(xoffset,y,zoffset)),\
                                             ZNorm).extrude(Base.Vector(0,0,BirchPanel.Thickness())))
            y += self.FingerWidth*2
        self.wall = panel
    def CutZYfingers(self,*,startz=0,endz=0,yoffset=0,xoffset=0):
        z = startz
        YNorm=Base.Vector(0,1,0)
        panel = self.wall
        while z <= endz:
            panel = panel.cut(Part.makePlane(self.FingerWidth,\
                                             BirchPanel.Thickness(),\
                                             self.origin.add(Base.Vector(xoffset,yoffset,z)),\
                                             YNorm).extrude(Base.Vector(0,BirchPanel.Thickness(),0)))
            z += self.FingerWidth*2
        self.wall = panel
    def AddPanel(self,*,xoffset=0,yoffset=0,zoffset=0,width=0,height=0):
        if self.side == 'Front':
            extrude = Base.Vector(0,BirchPanel.Thickness(),0)
            panel = Part.makePlane(height,
                                   width,
                                   self.origin.add(Base.Vector(xoffset,
                                                               yoffset,
                                                               zoffset)),
                                   Base.Vector(0,1,0)).extrude(extrude)
            self.wall = self.wall.fuse(panel)
        elif self.side == 'Left':
            extrude = Base.Vector(-BirchPanel.Thickness(),0,0)
            panel = Part.makePlane(height,
                                   width,
                                   self.origin.add(Base.Vector(xoffset+
                                                               BirchPanel.Thickness(),
                                                               yoffset,
                                                               zoffset+
                                                               height)),
                                   Base.Vector(-1,0,0)).extrude(extrude)
            self.wall = self.wall.fuse(panel)
        elif self.side == 'Right':
            extrude = Base.Vector(BirchPanel.Thickness(),0,0)
            panel = Part.makePlane(height,
                                   width,
                                   self.origin.add(Base.Vector(xoffset,
                                                               yoffset,
                                                               zoffset)),
                                   Base.Vector(1,0,0)).extrude(extrude)
            self.wall = self.wall.fuse(panel)
    def CutPanel(self,*,xoffset=0,yoffset=0,zoffset=0,width=0,height=0):
        if self.side == 'Front':
            extrude = Base.Vector(0,BirchPanel.Thickness(),0)
            panel = Part.makePlane(height,
                                   width,
                                   self.origin.add(Base.Vector(xoffset,
                                                               yoffset,
                                                               zoffset)),
                                   Base.Vector(0,1,0)).extrude(extrude)
            self.wall = self.wall.cut(panel)
        elif self.side == 'Left':
            extrude = Base.Vector(-BirchPanel.Thickness(),0,0)
            panel = Part.makePlane(height,
                                   width,
                                   self.origin.add(Base.Vector(xoffset,
                                                               yoffset,
                                                               zoffset)),
                                   Base.Vector(-1,0,0)).extrude(extrude)
            self.wall = self.wall.cut(panel)
        elif self.side == 'Right':
            extrude = Base.Vector(BirchPanel.Thickness(),0,0)
            panel = Part.makePlane(height,
                                   width,
                                   self.origin.add(Base.Vector(xoffset,
                                                               yoffset,
                                                               zoffset)),
                                   Base.Vector(1,0,0)).extrude(extrude)
            self.wall = self.wall.cut(panel)
    def Cut(self,otherWall):
        self.wall = self.wall.cut(otherWall.wall)
    def show(self,doc=None):
        if doc==None:
            doc = App.activeDocument()
        obj = doc.addObject("Part::Feature",self.name)
        obj.Shape = self.wall
        obj.Label=self.name
        obj.ViewObject.ShapeColor=self.Color
        for w in self.windows:
            w.show(doc)
    def PanelPage(self,techDoc,page,lastX,lastY,deltaY,*,minX=50,minY=50,
                                             maxX=(24*25.4)-50,
                                             maxY=(16*25.4)-50):
        #print("*** WallPanel.PanelPage(): page is ",page)
        #print("*** WallPanel.PanelPage(): lastX = ",lastX,", lastY = ",lastY)
        bbox = self.wall.BoundBox
        #print("*** WallPanel.PanelPage(): bbox = ",bbox)
        if self.side == 'Front':
            direction = Base.Vector(0,1,0)
            lengthX = bbox.XLength
            lengthY = bbox.ZLength
        elif self.side == 'Left':
            direction = Base.Vector(-1,0,0)
            lengthX = bbox.YLength
            lengthY = bbox.ZLength
        elif self.side == 'Right':
            direction = Base.Vector(1,0,0)
            lengthX = bbox.YLength
            lengthY = bbox.ZLength
        elif self.side == 'Rear':
            direction = Base.Vector(0,-1,0)
            lengthX = bbox.XLength
            lengthY = bbox.ZLength
        fitP, currentX, currentY, lengthX, lengthY, deltaY, rotation = \
            BirchPanel.FitPanel(page,lastX,lastY,lengthX,lengthY,deltaY,minX,
                                minY, maxX,maxY)
        if not fitP:
            return (True, -1, -1, deltaY)
        #print("*** WallPanel.PanelPage(): currentX = ",currentX,", currentY = ",currentY)
        #print("*** WallPanel.PanelPage(): lengthX = ",lengthX,", lengthY = ", lengthY)
        #print("*** WallPanel.PanelPage(): rotation = ",rotation)
        obj = techDoc.addObject("Part::Feature",self.name)
        obj.Shape = self.wall
        obj.ViewObject.Visibility = False
        panel = techDoc.addObject('TechDraw::DrawViewPart',self.name+"_View")
        page.addView(panel)
        panel.Source = obj
        panel.X = currentX+lengthX/2
        panel.Y = currentY+lengthY/2
        panel.Rotation = rotation
        panel.Direction = direction
        return (True,currentX+lengthX+10,currentY,deltaY)

class Floor(BirchPanel, InstanceIter):
    def sortKey(self):
        bbox = self.floor.BoundBox
        a = bbox.XLength
        b = bbox.YLength
        return math.hypot(a,b)
    def __str__(self):
        try:
            result = '<Floor name="'+self.name+'"'
            result = result+', origin='+str(self.origin)
            result = result+'>'
            return result
        except BaseException:
            return "<Floor>"
    def __init__(self,name,origin,width,height):
        super(Floor,self).__init__()
        self.name = name
        if not isinstance(origin,Base.Vector):
            raise RuntimeError("origin is not a Vector!")
        self.origin = origin
        extrude = Base.Vector(0,0,BirchPanel.Thickness())
        panel = Part.makePlane(height,width,origin).extrude(extrude)
        self.floor = panel
    def Cut(self,wall):
        self.floor = self.floor.cut(wall.wall)
    def show(self,doc=None):
        if doc==None:
            doc = App.activeDocument()
        obj = doc.addObject("Part::Feature",self.name)
        obj.Shape = self.floor
        obj.Label=self.name
        obj.ViewObject.ShapeColor=self.Color
    def PanelPage(self,techDoc,page,lastX,lastY,deltaY,*,minX=50,minY=50,
                                             maxX=(24*25.4)-50,
                                             maxY=(16*25.4)-50):
        #print("*** Floor.PanelPage(): page is ",page)
        #print("*** Floor.PanelPage(): lastX = ",lastX,", lastY = ",lastY)
        bbox = self.floor.BoundBox
        #print("*** Floor.PanelPage(): bbox = ",bbox)
        lengthX = bbox.XLength
        lengthY = bbox.YLength
        fitP, currentX, currentY, lengthX, lengthY, deltaY, rotation = \
            BirchPanel.FitPanel(page,lastX,lastY,lengthX,lengthY,deltaY,minX,minY,
                                maxX,maxY)
        if not fitP:
            return (True, -1, -1, deltaY)
        #print("*** Floor.PanelPage(): currentX = ",currentX,", currentY = ",currentY)
        #print("*** Floor.PanelPage(): lengthX = ",lengthX,", lengthY = ", lengthY)
        #print("*** Floor.PanelPage(): rotation = ",rotation)
        obj = techDoc.addObject("Part::Feature",self.name)
        obj.Shape = self.floor
        obj.ViewObject.Visibility = False
        panel = techDoc.addObject('TechDraw::DrawViewPart',self.name+"_View")
        page.addView(panel)
        panel.Source = obj
        panel.X = currentX+lengthX/2
        panel.Y = currentY+lengthY/2
        panel.Rotation = rotation
        panel.Direction = (0,0,1)
        return (True,currentX+lengthX+10,currentY,deltaY)



class EntryWayAndDoor(object):
    __baseDepth = 183.25379943847656-115.00755310058594
    __baseWidth = 48.76459503173828*2
    __baseHeight = 2.797820568084717-(-18.654172897338867)
    __stepsXOffset = 48.76459503173828-38.98531723022461
    __stepsWidth = 38.98531723022461*2
    __stepsDepths= [183.25379943847656-150.29324340820312,
                    183.25379943847656-158.53338623046875,
                    183.25379943847656-166.77352905273438,
                    183.25379943847656-175.01365661621094]
    __stepsZOffset=[-2.572909116744995-(-18.654172897338867),
                    -7.933324813842773-(-18.654172897338867),
                    -13.293740272521973-(-18.654172897338867),
                    -18.654155731201172-(-18.654172897338867)]
    __frontIndentWidth = (-40.49898910522461)-(-47.277015686035156)
    __frontIndentHeight = (1.3102514743804932)-(-17.166584014892578)
    __frontIndentXOffset = -47.277015686035156-(-48.76459503173828)
    __frontIndentZOffset = (-17.166584014892578)-(-18.654163360595703)
    __frontIndentDepth = 183.253799438476-182.65151977539062
    __frontCoverRoundRadius=.34346008300782
    __frontCoverThickness = .34346008300782*2
    __frontCoverWidth = (-39.0117073059082) - (-49.463340759277344)
    __frontCoverLength = 183.9518737792-115.007431030273
    __columBaseWidth = 16.088188171386718
    __columBaseDepth = 16.08079528808592
    __columBaseHeight = 14.0555922985076906 
    __columCenterY = 134.2124481201172 - 115.00755310058594 + \
                        ((150.29324340820312-134.2124481201172)/2)
    __columBaseCoverThickness = 1.689676284790038
    __columBaseCoverRoundRadius=1.689676284790038/2
    __columBaseCoverWidth=16.933029174804678
    __columBaseCoverDepth=16.92539978027340
    __columBaseRadius = 5.95060729980468
    __columTopRadius  = 5.95060729980468 - 1.61177062988282
    __columHeight = 77.13805389404297 - 18.537721633911133
    __columnC1Radius = (5.95060729980468 - 1.61177062988282)+.39648437500006
    __columnC1Height = 1.00946044921875
    __columnC2Radius = (5.95060729980468 - 1.61177062988282)+.39648437500006 +\
                        .54496765136719
    __columnC2Height = 2.83856964111328
    __columnC3Radius = (5.95060729980468 - 1.61177062988282)+.39648437500006 +\
                        .54496765136719 + 1.96015930175781
    __columnC3Height = 3.67766571044922
    __backWallXOff = -39.0117073059082 - (-48.76459503173828)
    __backWallDepth = 124.75366973876953-115.00755310058594
    __backWallWidth = 38.98501968383789 - (-39.0117073059082)
    __backWallHeight = 16.08079528808592+1.689676284790038+\
                       (77.13805389404297 - 18.537721633911133)+\
                       1.00946044921875+2.83856964111328+3.67766571044922
    __outerDoorWayXOffset = -18.049304962158203 - (-48.76459503173828)
    __outerDoorWayZOffset = 7.670636177062988 - (-18.654172897338867)
    __outerDoorWayMinorRadius = 18
    __outerDoorWayMajorRadius = 24.2
    __outerDoorWayBottomRectHeight = 44.8
    __outerDoorWayBottomRectWidth  = 36
    __outerDoorWayDepth = (124.75366973876953-115.00755310058594)+10
    __doorOuterTunnelXOffset = -25.897098541259766 - (-48.76459503173828)
    __doorOuterTunnelZOffset = 7.670637130737305 - (-18.654172897338867)
    __doorOuterTunnelMinorRadius = 25.897098541259766
    __doorOuterTunnelMajorRadius = 26.862136840820306
    __doorOuterTunnelBottomRectHeight = 52.690696716308594-7.670637130737305
    __doorOuterTunnelBottomRectWidth = 25.897098541259766*2
    __doorTunnelDepth = 115.00755310058594-101.24455261230469
    __doorInnerTunnelXOffset = -21.04060935974121 - (-48.76459503173828)
    __doorInnerTunnelZOffset = 7.670637130737305 - (-18.654172897338867)
    __doorInnerTunnelMinorRadius = 21.04060935974121
    __doorInnerTunnelMajorRadius = 22.0741081237793
    __doorInnerTunnelBottomRectHeight = 52.6026496887207-7.670637130737305
    __doorInnerTunnelBottomRectWidth = 21.04060935974121*2
    __doorThickness = (1.0/16.0)*25.4
    __doorClearance = .5
    __doorHingeBlock1Z = 12.5
    __doorHingeBlock2Z = 44.432012557983395-(12.5*1.5)
    __doorHingeBlockH  = 12.5*.5
    __doorHingeBlockPinR = .5
    __doorPullWidth = (1/8)*25.4
    __doorPullThickness = (1.0/16.0)*25.4 
    __doorPullWireHoleR = (1/64)*25.4
    __entrywayRoofDepth = 162.4363250732422-115.00755310058594
    __entrywayRoofHeight = 88.55018615722656-84.65019226074219
    __entrywayRoofZOffset = 84.65019226074219-(-18.654172897338867)
    __lightCenterX = 0 - (-48.76459503173828)
    __lightCenterY = 115.00755310058594 - \
                        ((149.23240661621094+137.95774841308594)/2)
    __lightBaseRadius = 11.27465820312500/2
    __lightBaseHeight = 84.72457885742188 - 80.42092895507812
    __lightDrop = 80.42092895507812-70.61669921875
    __lightGlobeRadius = (70.61669921875-62.1161003112793)/2
    __lightHoleRadius = (1/16)*25.4
    __lightBaseColor = (139/255, 117/255,   0.0)
    __lightWireColor = (0.25, 0.0, 0.0)
    __lightGlobeColor = (1.0, 1.0, 1.0)
    __entrywayColor=(.7,.7, .7)
    __doorColor=(139/255, 35/255, 35/255)
    def __makeDoors(self):
        doorYOffset = self.__doorTunnelDepth - self.__doorThickness
        doorOrigin = self.origin.add(Base.Vector(
                self.__doorInnerTunnelXOffset+self.__doorClearance,
                doorYOffset,
                self.__doorInnerTunnelZOffset+self.__doorClearance))
        doorArchOrig = doorOrigin.add(Base.Vector(
                self.__doorInnerTunnelMinorRadius-self.__doorClearance,0,
                self.__doorInnerTunnelBottomRectHeight-self.__doorClearance))
        doorMajor = doorArchOrig.add(
                Base.Vector(0,0,self.__doorInnerTunnelMajorRadius-
                                self.__doorClearance))
        doorMinor = doorArchOrig.add(
                Base.Vector((-self.__doorInnerTunnelMinorRadius)+
                            self.__doorClearance,0,0))
        doorExtrude  = Base.Vector(0,self.__doorThickness,0)
        doorEllipse=Part.Ellipse(doorMajor,doorMinor,doorArchOrig)
        doorWire = Part.Wire(doorEllipse.toShape())
        doorFace = Part.Face(doorWire)
        doorArch = doorFace.extrude(doorExtrude)
        doorBase = Part.makePlane(self.__doorInnerTunnelBottomRectHeight-
                                    self.__doorClearance,
                                  self.__doorInnerTunnelBottomRectWidth-
                                    (self.__doorClearance*2),
                                  doorOrigin,
                                  Base.Vector(0,1,0)
                                  ).extrude(doorExtrude)
        bothDoors = doorBase.fuse(doorArch)
        slicer = Part.makePlane(self.__doorInnerTunnelBottomRectHeight*2,
                                (self.__doorInnerTunnelBottomRectWidth/2)+
                                self.__doorClearance,
                                doorOrigin,
                                Base.Vector(0,1,0)
                                ).extrude(doorExtrude)
        rightDoor = bothDoors.cut(slicer)
        rightDoor = self.__addHinges(rightDoor,'Right')
        rightDoor = self.__addPull(rightDoor,'Right')
        self.rightDoor = rightDoor
        slicer = Part.makePlane(self.__doorInnerTunnelBottomRectHeight*2,
                                (self.__doorInnerTunnelBottomRectWidth/2),
                                doorOrigin.add(
                        Base.Vector((self.__doorInnerTunnelBottomRectWidth/2)-
                                    self.__doorClearance,0,0)),
                                Base.Vector(0,1,0)
                                ).extrude(doorExtrude)
        leftDoor = bothDoors.cut(slicer)
        leftDoor = self.__addHinges(leftDoor,'Left')
        leftDoor = self.__addPull(leftDoor,'Left')
        self.leftDoor = leftDoor
    def __addPull(self,door,side):
        doorYOffset = self.__doorTunnelDepth
        if side=='Right':
            pullBlockOrigin = self.origin.add(
               Base.Vector(self.__doorInnerTunnelXOffset+
                           self.__doorClearance*3+
                           ((self.__doorInnerTunnelBottomRectWidth-
                             self.__doorClearance)/2),
                           doorYOffset,
                           self.__doorInnerTunnelZOffset+
                           self.__doorClearance+
                           (self.__doorHingeBlock1Z+
                            self.__doorHingeBlock2Z)/2))
        elif side=='Left':
            pullBlockOrigin = self.origin.add(
               Base.Vector(self.__doorInnerTunnelXOffset+
                           ((self.__doorInnerTunnelBottomRectWidth-
                             self.__doorClearance)/2)-
                           self.__doorPullWidth,
                           doorYOffset,
                           self.__doorInnerTunnelZOffset+
                           self.__doorClearance+
                           (self.__doorHingeBlock1Z+
                            self.__doorHingeBlock2Z)/2))
        else:
            raise RuntimeError("unsupported side: %s"%(side))
        block = Part.makePlane(self.__doorPullWidth,
                               self.__doorPullWidth,
                               pullBlockOrigin
                               ).extrude(
                                    Base.Vector(0,0,self.__doorPullThickness))
        wirehole = Part.Face(Part.Wire(
            Part.makeCircle(self.__doorPullWireHoleR,
                            pullBlockOrigin.add(
                                Base.Vector(self.__doorPullWidth/2,
                                            self.__doorPullWidth/2,
                                            0))))
              ).extrude(Base.Vector(0,0,self.__doorPullThickness))
        block = block.cut(wirehole)        
        return door.fuse(block)
    def __addHinges(self,door,side):
        doorYOffset = self.__doorTunnelDepth - self.__doorThickness
        if side=='Right':
            hingeBlock1Origin = self.origin.add(
                Base.Vector(self.__doorInnerTunnelXOffset+
                            self.__doorInnerTunnelBottomRectWidth-
                            self.__doorClearance,
                            doorYOffset,
                            self.__doorInnerTunnelZOffset+
                            self.__doorClearance+
                            self.__doorHingeBlock1Z))
            hingeBlock2Origin = self.origin.add(
                Base.Vector(self.__doorInnerTunnelXOffset+
                            self.__doorInnerTunnelBottomRectWidth-
                            self.__doorClearance,
                            doorYOffset,
                            self.__doorInnerTunnelZOffset+
                            self.__doorClearance+
                            self.__doorHingeBlock2Z))
            CylinderOffset=Base.Vector(self.__doorThickness*2,
                                       self.__doorThickness/2,0)
            CutOffset     =Base.Vector(0,0,0)
            blockoffset   =Base.Vector(0,0,0)
            pinblockoffset = -self.__doorThickness*2
        elif side=='Left':
            hingeBlock1Origin = self.origin.add(
                Base.Vector(self.__doorInnerTunnelXOffset+
                            self.__doorClearance,
                            doorYOffset,
                            self.__doorInnerTunnelZOffset+
                            self.__doorClearance+
                            self.__doorHingeBlock1Z))
            hingeBlock2Origin = self.origin.add(
                Base.Vector(self.__doorInnerTunnelXOffset+
                            self.__doorClearance,
                            doorYOffset,
                            self.__doorInnerTunnelZOffset+
                            self.__doorClearance+
                            self.__doorHingeBlock2Z))
            CylinderOffset=Base.Vector(-self.__doorThickness*2,
                                       self.__doorThickness/2,0)
            CutOffset     =Base.Vector(-self.__doorThickness*2.5,0,0)
            blockoffset   =Base.Vector(-self.__doorThickness*2,0,0)
            pinblockoffset = 0
        else:
            raise RuntimeError("unsupported side: %s"%(side))
        cut=Part.makePlane(self.__doorThickness*2.5,
                           self.__doorThickness,
                           hingeBlock1Origin.add(CutOffset)).extrude(
                                    Base.Vector(0,0,self.__doorHingeBlockH))
        self.entryway = self.entryway.cut(cut)
        Cylinder = Part.Face(Part.Wire(
                    Part.makeCircle(self.__doorThickness/2,
                                    hingeBlock1Origin.add(CylinderOffset)
                                    ))).extrude(
                                       Base.Vector(0,0,self.__doorHingeBlockH))
        hblock = Part.makePlane(self.__doorThickness*2,
                                self.__doorThickness,
                                hingeBlock1Origin.add(blockoffset)).extrude(
                                        Base.Vector(0,0,self.__doorHingeBlockH))
        door = door.fuse(hblock).fuse(Cylinder)
        pin = Part.Face(Part.Wire(
                Part.makeCircle(self.__doorHingeBlockPinR,
                        hingeBlock1Origin.add(CylinderOffset).add(
                            Base.Vector(0,0,-self.__doorClearance))
                            ))).extrude(
                                  Base.Vector(0,0,self.__doorHingeBlockH+
                                                (2*self.__doorClearance)))
        door = door.fuse(pin)
        pin1= Part.Face(Part.Wire(
                Part.makeCircle(self.__doorHingeBlockPinR*1.2,
                        hingeBlock1Origin.add(CylinderOffset).add(
                            Base.Vector(0,0,-self.__doorClearance))
                            ))).extrude(
                                  Base.Vector(0,0,self.__doorHingeBlockH+
                                                (2*self.__doorClearance)))
        block1=Part.makePlane(self.__doorThickness*2,
                              self.__doorHingeBlockPinR*2.4,
                              hingeBlock1Origin.add(CylinderOffset).add(
                                  Base.Vector(pinblockoffset,
                                              -self.__doorHingeBlockPinR*1.2,
                                              -self.__doorClearance))
                              ).extrude(
                                    Base.Vector(0,0,self.__doorHingeBlockH+
                                                (2*self.__doorClearance)))
        self.entryway = self.entryway.cut(block1.fuse(pin1))
        
        cut=Part.makePlane(self.__doorThickness*2.5,
                           self.__doorThickness,
                           hingeBlock2Origin.add(CutOffset)).extrude(
                                    Base.Vector(0,0,self.__doorHingeBlockH))
        self.entryway = self.entryway.cut(cut)
        Cylinder = Part.Face(Part.Wire(
                    Part.makeCircle(self.__doorThickness/2,
                                    hingeBlock2Origin.add(CylinderOffset)
                                    ))).extrude(
                                       Base.Vector(0,0,self.__doorHingeBlockH))
        hblock = Part.makePlane(self.__doorThickness*2,
                                self.__doorThickness,
                                hingeBlock2Origin.add(blockoffset)).extrude(
                                        Base.Vector(0,0,self.__doorHingeBlockH))
        door = door.fuse(hblock).fuse(Cylinder)
        pin = Part.Face(Part.Wire(
                Part.makeCircle(self.__doorHingeBlockPinR,
                        hingeBlock2Origin.add(CylinderOffset).add(
                            Base.Vector(0,0,-self.__doorClearance))
                            ))).extrude(
                                  Base.Vector(0,0,self.__doorHingeBlockH+
                                                (2*self.__doorClearance)))
        door = door.fuse(pin)
        pin1= Part.Face(Part.Wire(
                Part.makeCircle(self.__doorHingeBlockPinR*1.2,
                        hingeBlock2Origin.add(CylinderOffset).add(
                            Base.Vector(0,0,-self.__doorClearance))
                            ))).extrude(
                                  Base.Vector(0,0,self.__doorHingeBlockH+
                                                (2*self.__doorClearance)))
        block1=Part.makePlane(self.__doorThickness*2,
                              self.__doorHingeBlockPinR*2.4,
                              hingeBlock2Origin.add(CylinderOffset).add(
                                  Base.Vector(pinblockoffset,
                                              -self.__doorHingeBlockPinR*1.2,
                                              -self.__doorClearance))
                              ).extrude(
                                    Base.Vector(0,0,self.__doorHingeBlockH+
                                                (2*self.__doorClearance)))
        self.entryway = self.entryway.cut(block1.fuse(pin1))
                           
        return door
    def __init__(self,name,origin):
        self.name = name
        if not isinstance(origin,Base.Vector):
            raise RuntimeError("origin is not a Vector!")
        self.origin = origin
        base = Part.makePlane(self.__baseWidth,self.__baseDepth,
                              origin.add(Base.Vector(0,-self.__baseDepth,0)),
                              Base.Vector(0,0,1)).extrude(
                                        Base.Vector(0,0,self.__baseHeight))
        for sd,sz in zip(self.__stepsDepths,self.__stepsZOffset):
            stepcut = Part.makePlane(self.__stepsWidth,sd,
                                     origin.add(Base.Vector(
                                                self.__stepsXOffset,
                                                -self.__baseDepth,
                                                sz)),
                                     Base.Vector(0,0,1)).extrude(
                                        Base.Vector(0,0,self.__baseHeight-sz))
            base = base.cut(stepcut)
        frontIndent = Part.makePlane(self.__frontIndentHeight,
                                     self.__frontIndentWidth,
                                     origin.add(Base.Vector(
                                            self.__frontIndentXOffset,
                                            -self.__baseDepth,
                                            self.__frontIndentZOffset)),
                                     Base.Vector(0,1,0)
                         ).extrude(Base.Vector(0,self.__frontIndentDepth,0))
        base = base.cut(frontIndent)
        frontIndent = Part.makePlane(self.__frontIndentHeight,
                                     self.__frontIndentWidth,
                                     origin.add(Base.Vector(
                                            self.__baseWidth -
                                                (self.__frontIndentXOffset+
                                                 self.__frontIndentWidth),
                                            -self.__baseDepth,
                                            self.__frontIndentZOffset)),
                                     Base.Vector(0,1,0)
                         ).extrude(Base.Vector(0,self.__frontIndentDepth,0))
        base = base.cut(frontIndent)
        sidewidth = (self.__baseWidth-self.__stepsWidth)/2
        
        frontCoverOrigin = origin.add(
            Base.Vector(-((self.__frontCoverWidth-sidewidth)/2),
                        -self.__frontCoverLength,
                        self.__baseHeight))
        frontCover = self.__makeFrontCover(frontCoverOrigin)
        base = base.fuse(frontCover)
        frontCoverOrigin = origin.add(
            Base.Vector(self.__baseWidth-sidewidth
                        -((self.__frontCoverWidth-sidewidth)/2),
                        -self.__frontCoverLength,
                        self.__baseHeight))
        frontCover = self.__makeFrontCover(frontCoverOrigin)
        base = base.fuse(frontCover)
        columCenterOrigin = origin.add(Base.Vector(self.__stepsXOffset+
                                                    self.__columBaseWidth/2,
                                                    -self.__columCenterY,
                                                    self.__baseHeight))
        columnWithBase = self.__makecolumnWithBase(columCenterOrigin)
        base = base.fuse(columnWithBase)
        columCenterOrigin = origin.add(Base.Vector(self.__baseWidth-
                                                    self.__stepsXOffset-
                                                    self.__columBaseWidth/2,
                                                    -self.__columCenterY,
                                                    self.__baseHeight))
        columnWithBase = self.__makecolumnWithBase(columCenterOrigin)
        base = base.fuse(columnWithBase)
        backwall = Part.makePlane(self.__backWallWidth,
                                  self.__backWallDepth,
                                  origin.add(Base.Vector(self.__backWallXOff,
                                                         -self.__backWallDepth,
                                                         self.__baseHeight))
                                  ).extrude(Base.Vector(0,0,self.__backWallHeight))
        outerDoorWayTunnelOrigin = origin.add(Base.Vector(
                    self.__outerDoorWayXOffset,0,self.__outerDoorWayZOffset))
        outerDoorWayTunnelArchOrig = outerDoorWayTunnelOrigin.add(
                            Base.Vector(self.__outerDoorWayMinorRadius,0,
                                        self.__outerDoorWayBottomRectHeight))
        outerDoorWayTunnelMajor = outerDoorWayTunnelArchOrig.add(
                            Base.Vector(0,0,self.__outerDoorWayMajorRadius))
        outerDoorWayTunnelMinor = outerDoorWayTunnelArchOrig.add(
                            Base.Vector(-self.__outerDoorWayMinorRadius,0,0))
        outerDoorWayTunnelExtrude = Base.Vector(0,-self.__outerDoorWayDepth,0)
        outerDoorWayTunnelEllipse=Part.Ellipse(
                    outerDoorWayTunnelMajor,
                    outerDoorWayTunnelMinor,
                    outerDoorWayTunnelArchOrig)
        outerDoorWayTunnelWire = Part.Wire(outerDoorWayTunnelEllipse.toShape())
        outerDoorWayTunnelFace = Part.Face(outerDoorWayTunnelWire)
        outerDoorWayTunnelArch = outerDoorWayTunnelFace.extrude(outerDoorWayTunnelExtrude)
        outerDoorWayTunnelBase = Part.makePlane(self.__outerDoorWayBottomRectHeight,
                                                self.__outerDoorWayBottomRectWidth,
                                                outerDoorWayTunnelOrigin,
                                                Base.Vector(0,1,0)
                                                ).extrude(outerDoorWayTunnelExtrude)
                                                
        self.outerDoorWayTunnel =  outerDoorWayTunnelBase.fuse(outerDoorWayTunnelArch)
        backwall = backwall.cut(self.outerDoorWayTunnel)
        
        doorOuterTunnelOrig=origin.add(Base.Vector( 
                self.__doorOuterTunnelXOffset,0,
                self.__doorOuterTunnelZOffset))
        doorOuterTunnelArchOrig = doorOuterTunnelOrig.add(Base.Vector(
                self.__doorOuterTunnelMinorRadius,0,
                self.__doorOuterTunnelBottomRectHeight))
        doorOuterTunnelMajor = doorOuterTunnelArchOrig.add(
                            Base.Vector(0,0,self.__doorOuterTunnelMajorRadius))
        doorOuterTunnelMinor = doorOuterTunnelArchOrig.add(
                            Base.Vector(-self.__doorOuterTunnelMinorRadius,0,0))
        doorOuterTunnelExtrude = Base.Vector(0,self.__doorTunnelDepth,0)
        doorOuterTunnelEllipse=Part.Ellipse(
                    doorOuterTunnelMajor,
                    doorOuterTunnelMinor,
                    doorOuterTunnelArchOrig)
        doorOuterTunnelWire = Part.Wire(doorOuterTunnelEllipse.toShape())
        doorOuterTunnelFace = Part.Face(doorOuterTunnelWire)
        doorOuterTunnelArch = doorOuterTunnelFace.extrude(doorOuterTunnelExtrude)
        doorOuterTunnelBase = Part.makePlane(self.__doorOuterTunnelBottomRectHeight,
                                                self.__doorOuterTunnelBottomRectWidth,
                                                doorOuterTunnelOrig,
                                                Base.Vector(0,1,0)
                                                ).extrude(doorOuterTunnelExtrude)
                                                
        self.doorOuterTunnel =  doorOuterTunnelBase.fuse(doorOuterTunnelArch)

        doorInnerTunnelOrig=origin.add(Base.Vector(
                self.__doorInnerTunnelXOffset,0,
                self.__doorInnerTunnelZOffset))        
        doorInnerTunnelArchOrig = doorInnerTunnelOrig.add(Base.Vector(
                self.__doorInnerTunnelMinorRadius,0,
                self.__doorInnerTunnelBottomRectHeight))
        doorInnerTunnelMajor = doorInnerTunnelArchOrig.add(
                            Base.Vector(0,0,self.__doorInnerTunnelMajorRadius))
        doorInnerTunnelMinor = doorInnerTunnelArchOrig.add(
                            Base.Vector(-self.__doorInnerTunnelMinorRadius,0,0))
        doorInnerTunnelExtrude = Base.Vector(0,self.__doorTunnelDepth,0)
        doorInnerTunnelEllipse=Part.Ellipse(
                    doorInnerTunnelMajor,
                    doorInnerTunnelMinor,
                    doorInnerTunnelArchOrig)
        doorInnerTunnelWire = Part.Wire(doorInnerTunnelEllipse.toShape())
        doorInnerTunnelFace = Part.Face(doorInnerTunnelWire)
        doorInnerTunnelArch = doorInnerTunnelFace.extrude(doorInnerTunnelExtrude)
        doorInnerTunnelBase = Part.makePlane(self.__doorInnerTunnelBottomRectHeight,
                                                self.__doorInnerTunnelBottomRectWidth,
                                                doorInnerTunnelOrig,
                                                Base.Vector(0,1,0)
                                                ).extrude(doorInnerTunnelExtrude)
                                                
        self.doorInnerTunnel =  doorInnerTunnelBase.fuse(doorInnerTunnelArch)
        base = base.fuse(self.doorOuterTunnel.cut(self.doorInnerTunnel))

        base = base.fuse(backwall)
        roof = Part.makePlane(self.__backWallWidth,self.__entrywayRoofDepth,
                              origin.add(
                                    Base.Vector(self.__backWallXOff,
                                                -self.__entrywayRoofDepth, 
                                                self.__entrywayRoofZOffset))
                              ).extrude(Base.Vector(0,0,self.__entrywayRoofHeight))
        base = base.fuse(roof)
        self.entryway = base
        self.__makeDoors()
        lightFixtureOrigin = origin.add(Base.Vector(self.__lightCenterX,
                                                    self.__lightCenterY,
                                                    self.__entrywayRoofZOffset))
        lightWireHole=Part.Face(Part.Wire(
            Part.makeCircle(self.__lightHoleRadius,
                            lightFixtureOrigin))).extrude(
                                Base.Vector(0,0,self.__entrywayRoofHeight))
        self.entryway = self.entryway.cut(lightWireHole)
        lightWireHole=Part.Face(Part.Wire(
            Part.makeCircle(self.__lightHoleRadius,
                            lightFixtureOrigin))).extrude(
                                Base.Vector(0,0,-(self.__lightBaseHeight+
                                                  self.__lightDrop+
                                                  self.__lightGlobeRadius)))
        self.lightBase = Part.makeCone(self.__lightBaseRadius,
                                       0.0,
                                       self.__lightBaseHeight,
                                       lightFixtureOrigin,
                                       Base.Vector(0,0,-1))
        self.lightBase = self.lightBase.cut(lightWireHole)
        self.lightWire = Part.Face(Part.Wire(
            Part.makeCircle(self.__lightHoleRadius/2,
                            lightFixtureOrigin))).extrude(
                                Base.Vector(0,0,-(self.__lightBaseHeight+
                                                  self.__lightDrop+
                                                  self.__lightGlobeRadius)))
        lightGlobeOrigin = lightFixtureOrigin.add(
                Base.Vector(0,0,-(self.__lightBaseHeight+
                                  self.__lightDrop+
                                  self.__lightGlobeRadius)))
        self.lightGlobe = Part.makeSphere(self.__lightGlobeRadius,
                                            lightGlobeOrigin)
    def CutDoorTunnelFromPanel(self,panel):
        return panel.cut(self.doorOuterTunnel)
    def __makecolumnWithBase(self,columCenterOrigin):
        baseOrigin = columCenterOrigin.add(
                Base.Vector(-(self.__columBaseWidth/2),
                            -(self.__columBaseDepth/2),0))
        columnWithBase = Part.makePlane(self.__columBaseWidth,
                                         self.__columBaseDepth,
                                         baseOrigin,
                                         Base.Vector(0,0,1)).extrude(
                                            Base.Vector(0,0,
                                                    self.__columBaseHeight))
        columBaseCover = self.__makeColumnBaseCover(baseOrigin.add(
                                            Base.Vector(-(self.__columBaseCoverWidth-self.__columBaseWidth)/2,
                                                        -(self.__columBaseCoverDepth-self.__columBaseDepth)/2,
                                                        self.__columBaseHeight)))

        columnWithBase = columnWithBase.fuse(columBaseCover)
        column = Part.makeCone(self.__columBaseRadius,
                               self.__columTopRadius,
                               self.__columHeight,
                               columCenterOrigin.add(
                                Base.Vector(0,0,self.__columBaseHeight+
                                                self.__columBaseCoverThickness)))
        columnWithBase = columnWithBase.fuse(column)
        c1 = Part.makeCircle(self.__columnC1Radius,
                             columCenterOrigin.add(
                                Base.Vector(0,0,self.__columBaseHeight+
                                                self.__columBaseCoverThickness+
                                                self.__columHeight)))
        c1 = Part.Face(Part.Wire(c1)).extrude(
                                Base.Vector(0,0,self.__columnC1Height))
        columnWithBase = columnWithBase.fuse(c1)
        c2 = Part.makeCircle(self.__columnC2Radius,
                             columCenterOrigin.add(
                                Base.Vector(0,0,self.__columBaseHeight+
                                                self.__columBaseCoverThickness+
                                                self.__columHeight+
                                                self.__columnC1Height
                                                )))
        c2 = Part.Face(Part.Wire(c2)).extrude(
                            Base.Vector(0,0,self.__columnC2Height))
        columnWithBase = columnWithBase.fuse(c2)
        c3 = Part.makeCircle(self.__columnC3Radius,
                             columCenterOrigin.add(
                                Base.Vector(0,0,self.__columBaseHeight+
                                                self.__columBaseCoverThickness+
                                                self.__columHeight+
                                                self.__columnC1Height+
                                                self.__columnC2Height)))
        c3 = Part.Face(Part.Wire(c3)).extrude(
                                Base.Vector(0,0,self.__columnC3Height))
        columnWithBase = columnWithBase.fuse(c3)
        return columnWithBase
    def __makeColumnBaseCover(self,columBaseCoverOrigin):
        columBaseCover = Part.makePlane(self.__columBaseCoverWidth,
                                         self.__columBaseCoverDepth,
                                         columBaseCoverOrigin,
                                         Base.Vector(0,0,1)).extrude(
                                            Base.Vector(0,0,
                                                    self.__columBaseCoverThickness))
        round1 = Part.makeCircle(self.__columBaseCoverRoundRadius,
                        columBaseCoverOrigin.add(
                             Base.Vector(0,
                                         -self.__columBaseCoverRoundRadius,
                                         self.__columBaseCoverRoundRadius)),
                        Base.Vector(0,-1,0))
        round1 = Part.Face(Part.Wire(round1)
                     ).extrude(Base.Vector(0,self.__columBaseCoverDepth+
                                             (self.__columBaseCoverRoundRadius*2),
                                             0))
        miter1 = Part.makePlane(self.__columBaseCoverThickness,
                                self.__columBaseCoverThickness,
                                columBaseCoverOrigin.add(
                                    Base.Vector(-self.__columBaseCoverRoundRadius,
                                                -self.__columBaseCoverRoundRadius,
                                                self.__columBaseCoverThickness)),
                                Base.Vector(1,1,0)).extrude(Base.Vector(
                                    self.__columBaseCoverThickness,
                                    self.__columBaseCoverThickness,0))
        round1 = round1.cut(miter1)
        miter1 = Part.makePlane(self.__columBaseCoverThickness,
                                self.__columBaseCoverThickness,
                                columBaseCoverOrigin.add(
                                    Base.Vector(-self.__columBaseCoverRoundRadius,
                                                self.__columBaseCoverDepth+
                                                self.__columBaseCoverRoundRadius,
                                                self.__columBaseCoverThickness)),
                                Base.Vector(1,1,0)).extrude(Base.Vector(
                                    self.__columBaseCoverThickness,
                                    self.__columBaseCoverThickness,0))
        round1 = round1.cut(miter1)
        columBaseCover = columBaseCover.fuse(round1)
        round1 = Part.makeCircle(self.__columBaseCoverRoundRadius,
                                 columBaseCoverOrigin.add(
                              Base.Vector(-self.__columBaseCoverRoundRadius,0
                                          ,self.__columBaseCoverRoundRadius)),
                                 Base.Vector(1,0,0))
        round1 = Part.Face(Part.Wire(round1)
                ).extrude(Base.Vector(self.__columBaseCoverWidth + 
                                        self.__columBaseCoverRoundRadius*2,0,0))
        miter1 = Part.makePlane(self.__columBaseCoverThickness,
                                self.__columBaseCoverThickness,
                                columBaseCoverOrigin.add(
                                    Base.Vector(self.__columBaseCoverRoundRadius,
                                                self.__columBaseCoverRoundRadius,
                                                self.__columBaseCoverThickness)),
                                 Base.Vector(-1,-1,0)).extrude(Base.Vector(
                                            -self.__columBaseCoverThickness,
                                            -self.__columBaseCoverThickness,0))
        round1 = round1.cut(miter1)
        miter1 = Part.makePlane(self.__columBaseCoverThickness,
                                self.__columBaseCoverThickness,
                                columBaseCoverOrigin.add(
                                    Base.Vector(self.__columBaseCoverWidth+
                                                self.__columBaseCoverRoundRadius,
                                                -self.__columBaseCoverRoundRadius,
                                                self.__columBaseCoverThickness)),
                                 Base.Vector(-1,1,0)).extrude(Base.Vector(
                                            -self.__columBaseCoverThickness,
                                            self.__columBaseCoverThickness,0))
        round1 = round1.cut(miter1)
        columBaseCover = columBaseCover.fuse(round1)
        round1 = Part.makeCircle(self.__columBaseCoverRoundRadius,
                                 columBaseCoverOrigin.add(
                              Base.Vector(self.__columBaseCoverWidth,
                                          -self.__columBaseCoverRoundRadius
                                          ,self.__columBaseCoverRoundRadius)),
                                 Base.Vector(0,-1,0))
        round1 = Part.Face(Part.Wire(round1)
                ).extrude(Base.Vector(0,self.__columBaseCoverDepth + 
                                        self.__columBaseCoverThickness,0))
        miter1 = Part.makePlane(self.__columBaseCoverThickness,
                                self.__columBaseCoverThickness,
                                columBaseCoverOrigin.add(
                                    Base.Vector(self.__columBaseCoverWidth+
                                                self.__columBaseCoverRoundRadius,
                                                -self.__columBaseCoverRoundRadius,
                                                self.__columBaseCoverThickness)),
                                 Base.Vector(-1,-1,0)).extrude(Base.Vector(
                                            -self.__columBaseCoverThickness,
                                            -self.__columBaseCoverThickness,0))
        round1 = round1.cut(miter1)
        miter1 = Part.makePlane(self.__columBaseCoverThickness,
                                self.__columBaseCoverThickness,
                                columBaseCoverOrigin.add(
                                    Base.Vector(self.__columBaseCoverWidth+
                                                self.__columBaseCoverRoundRadius,
                                                self.__columBaseCoverDepth+
                                                self.__columBaseCoverRoundRadius,
                                                self.__columBaseCoverThickness)),
                                 Base.Vector(-1,-1,0)).extrude(Base.Vector(
                                            -self.__columBaseCoverThickness,
                                            -self.__columBaseCoverThickness,0))
        round1 = round1.cut(miter1)
        columBaseCover = columBaseCover.fuse(round1)
        round1 = Part.makeCircle(self.__columBaseCoverRoundRadius,
                                 columBaseCoverOrigin.add(
                              Base.Vector(-self.__columBaseCoverRoundRadius,
                                          self.__columBaseCoverDepth,
                                          self.__columBaseCoverRoundRadius)),
                                 Base.Vector(1,0,0))
        round1 = Part.Face(Part.Wire(round1)
                ).extrude(Base.Vector(self.__columBaseCoverWidth + 
                                        self.__columBaseCoverRoundRadius*2,0,0))
        miter1 = Part.makePlane(self.__columBaseCoverThickness,
                                self.__columBaseCoverThickness,
                                columBaseCoverOrigin.add(
                                    Base.Vector(-self.__columBaseCoverRoundRadius,
                                                self.__columBaseCoverDepth+
                                                self.__columBaseCoverRoundRadius,
                                                self.__columBaseCoverThickness)),
                                 Base.Vector(1,-1,0)).extrude(Base.Vector(
                                            self.__columBaseCoverThickness,
                                            -self.__columBaseCoverThickness,0))
        round1 = round1.cut(miter1)
        miter1 = Part.makePlane(self.__columBaseCoverThickness,
                                self.__columBaseCoverThickness,
                                columBaseCoverOrigin.add(
                                    Base.Vector(self.__columBaseCoverWidth+
                                                self.__columBaseCoverThickness*1.45,
                                                self.__columBaseCoverDepth,
                                                self.__columBaseCoverThickness)),
                                 Base.Vector(-1,-1,0)).extrude(Base.Vector(
                                            -self.__columBaseCoverThickness,
                                            -self.__columBaseCoverThickness,0))
        round1 = round1.cut(miter1)
        columBaseCover = columBaseCover.fuse(round1)

        return columBaseCover
    def __makeFrontCover(self,frontCoverOrigin):
        frontCover = Part.makePlane(self.__frontCoverWidth,
                                    self.__frontCoverLength,
                                    frontCoverOrigin,
                                    Base.Vector(0,0,1)
                                    ).extrude(Base.Vector(
                                               0,0,self.__frontCoverThickness))
        round1 = Part.makeCircle(self.__frontCoverRoundRadius,
                                 frontCoverOrigin.add(
                              Base.Vector(0,-self.__frontCoverRoundRadius
                                          ,self.__frontCoverRoundRadius)),
                                 Base.Vector(0,-1,0))
        round1 = Part.Face(Part.Wire(round1)
                ).extrude(Base.Vector(0,self.__frontCoverLength + 
                                        self.__frontCoverRoundRadius,0))
        miter1 = Part.makePlane(self.__frontCoverThickness,
                                self.__frontCoverThickness,
                                frontCoverOrigin.add(
                                    Base.Vector(-self.__frontCoverRoundRadius,
                                                -self.__frontCoverRoundRadius,
                                                self.__frontCoverThickness)),
                                 Base.Vector(1,1,0)).extrude(Base.Vector(
                                            self.__frontCoverThickness,
                                            self.__frontCoverThickness,0))
        round1 = round1.cut(miter1)
        frontCover = frontCover.fuse(round1)
        round1 = Part.makeCircle(self.__frontCoverRoundRadius,
                                 frontCoverOrigin.add(
                              Base.Vector(-self.__frontCoverRoundRadius,0
                                          ,self.__frontCoverRoundRadius)),
                                 Base.Vector(1,0,0))
        round1 = Part.Face(Part.Wire(round1)
                ).extrude(Base.Vector(self.__frontCoverWidth + 
                                        self.__frontCoverRoundRadius*2,0,0))
        miter1 = Part.makePlane(self.__frontCoverThickness,
                                self.__frontCoverThickness,
                                frontCoverOrigin.add(
                                    Base.Vector(self.__frontCoverRoundRadius,
                                                self.__frontCoverRoundRadius,
                                                self.__frontCoverThickness)),
                                 Base.Vector(-1,-1,0)).extrude(Base.Vector(
                                            -self.__frontCoverThickness,
                                            -self.__frontCoverThickness,0))
        round1 = round1.cut(miter1)
        miter1 = Part.makePlane(self.__frontCoverThickness,
                                self.__frontCoverThickness,
                                frontCoverOrigin.add(
                                    Base.Vector(self.__frontCoverWidth+
                                                self.__frontCoverRoundRadius,
                                                -self.__frontCoverRoundRadius,
                                                self.__frontCoverThickness)),
                                 Base.Vector(-1,1,0)).extrude(Base.Vector(
                                            -self.__frontCoverThickness,
                                            self.__frontCoverThickness,0))
        round1 = round1.cut(miter1)
        frontCover = frontCover.fuse(round1)
        round1 = Part.makeCircle(self.__frontCoverRoundRadius,
                                 frontCoverOrigin.add(
                              Base.Vector(self.__frontCoverWidth,
                                          -self.__frontCoverRoundRadius
                                          ,self.__frontCoverRoundRadius)),
                                 Base.Vector(0,-1,0))
        round1 = Part.Face(Part.Wire(round1)
                ).extrude(Base.Vector(0,self.__frontCoverLength + 
                                        self.__frontCoverRoundRadius,0))
        miter1 = Part.makePlane(self.__frontCoverThickness,
                                self.__frontCoverThickness,
                                frontCoverOrigin.add(
                                    Base.Vector(self.__frontCoverWidth+
                                                self.__frontCoverRoundRadius,
                                                -self.__frontCoverRoundRadius,
                                                self.__frontCoverThickness)),
                                 Base.Vector(-1,-1,0)).extrude(Base.Vector(
                                            -self.__frontCoverThickness,
                                            -self.__frontCoverThickness,0))
        round1 = round1.cut(miter1)
        frontCover = frontCover.fuse(round1)
        return frontCover
    def show(self,doc=None):
        if doc==None:
            doc = App.activeDocument()
        obj = doc.addObject("Part::Feature",self.name+"_entryway")
        obj.Shape = self.entryway
        obj.Label=self.name+"_entryway"
        obj.ViewObject.ShapeColor=self.__entrywayColor
        obj = doc.addObject("Part::Feature",self.name+"_rightdoor")
        obj.Shape = self.rightDoor
        obj.Label=self.name+"_rightdoor"
        obj.ViewObject.ShapeColor=self.__doorColor
        obj = doc.addObject("Part::Feature",self.name+"_leftdoor")
        obj.Shape = self.leftDoor
        obj.Label=self.name+"_leftdoor"
        obj.ViewObject.ShapeColor=self.__doorColor
        obj = doc.addObject("Part::Feature",self.name+"_lightBase")
        obj.Shape = self.lightBase
        obj.Label=self.name+"_lightBase"
        obj.ViewObject.ShapeColor=self.__lightBaseColor
        obj = doc.addObject("Part::Feature",self.name+"_lightWire")
        obj.Shape = self.lightWire
        obj.Label=self.name+"_lightWire"
        obj.ViewObject.ShapeColor=self.__lightWireColor
        obj = doc.addObject("Part::Feature",self.name+"_lightGlobe")
        obj.Shape = self.lightGlobe
        obj.Label=self.name+"_lightGlobe"
        obj.ViewObject.ShapeColor=self.__lightGlobeColor

class GreenHouse(object):
    # Vector (156.03402709960938, -18.670608520507812, 89.00996398925781)
    # Vector (274.43206787109375, -18.670618057250977, 88.99929809570312)
    # Vector (274.43206787109375, -18.670618057250977, -29.339580535888672)
    # Vector (156.03402709960938, -18.670608520507812, -29.339040756225586)
    #
    # Vector (156.03402709960938, 106.17420959472656, 89.00996398925781)
    # Vector (274.43206787109375, 106.17420959472656, 88.98863220214844)
    # Vector (274.43206787109375, 106.17420959472656, -29.339580535888672)
    # Vector (156.03402709960938, 106.17420959472656, -29.339040756225586)
    __wallThickness = (1/8)*25.4
    __wallIndent = (1/16)*25.4
    
    __wallHeight = 106.17420959472656 - (-18.670608520507812)
    __length     = 274.43206787109375 - 156.03402709960938
    __width      = 88.99929809570312 - (-29.339580535888672)
    # Vector (162.48980712890625, 69.2083511352539, 86.07927703857422)
    # Vector (219.2116241455078, 69.20860290527344, 86.07868957519531)
    # Vector (162.4896697998047, -5.378434658050537, 86.07927703857422)
    # Vector (166.847412109375, -5.378434658050537, 86.07884979248047)
    # Vector (162.4896697998047, 1.3253087997436523, 86.07927703857422)
    # Vector (211.28485107421875, -5.378434658050537, 86.07450103759766)
    # Vector (162.48980712890625, 69.2083511352539, 86.07927703857422)
    # Vector (166.84666442871094, 69.2083511352539, 86.07905578613281)
    # Vector (162.4896697998047, 1.9050686359405518, 86.07927703857422)
    
    __window2Offset = 219.2116241455078 - 162.48980712890625
    __windowOffset = 162.48980712890625 - 156.03402709960938
    __windowBottom = -5.378434658050537 - (-18.670608520507812)
    __windowWidth = 211.28485107421875 - 162.48980712890625
    __windowBarWidth = 167.42715454101562 - 166.847412109375
    __upperWindowOffset = 75.51575469970703-69.2083511352539
    __upperWindowRadius = (210.8865966796875-162.88238525390625)/2
    __windowHeight = 69.2083511352539-(-5.378434658050537)
    __windowPaneWidth = 166.847412109375-162.4896697998047
    __windowPaneHeight = 1.3253087997436523 - (-5.378434658050537)
    __windowPaneXStride = 167.42715454101562 - 162.4896697998047
    __windowPaneZStride = 1.9050686359405518 - (-5.378434658050537)
    __upperBarWidth = 0.988888657334412 / 2
    __upperBarAngle = 90/4
    __color      = (.8, .8, .8)
    # Vector (156.03402709960938, 106.17420959472656, 89.00996398925781)
    # Vector (153.77389526367188, 103.75820922851562, 92.99351501464844)
    # Vector (153.8173828125, 106.4601058959961, 88.98295593261719)
    # Vector (274.7114562988281, 106.4601058959961, -28.89644432067871)
    __roofSTL = os.path.join(os.path.dirname(__file__),"GreenhouseRoof.stl")
    __roofOrigin = Base.Vector(0,-(126.03-118.34)/2,124.84)
    def __init__(self,name,origin):
        self.name = name
        if not isinstance(origin,Base.Vector):
            raise RuntimeError("origin is not a Vector!")
        self.origin = origin
        self.front=self.__wall('Front')
        self.right=self.__wall('Right')
        self.rear =self.__wall('Rear')
        self.roof = self.__roof()
    def show(self,doc=None):
        if doc==None:
            doc = App.activeDocument()
        obj = doc.addObject("Part::Feature",self.name+"_Front")
        obj.Shape = self.front
        obj.Label=self.name+"_Front"
        obj.ViewObject.ShapeColor=self.__color
        obj = doc.addObject("Part::Feature",self.name+"_Right")
        obj.Shape = self.right
        obj.Label=self.name+"_Right"
        obj.ViewObject.ShapeColor=self.__color
        obj = doc.addObject("Part::Feature",self.name+"_Rear")
        obj.Shape = self.rear
        obj.Label=self.name+"_Rear"
        obj.ViewObject.ShapeColor=self.__color
        obj = doc.addObject("Mesh::Feature",self.name+"_Roof")
        obj.Mesh = self.roof
        obj.Label=self.name+"_Roof"
        obj.ViewObject.ShapeColor=self.__color
        try:
            obj = doc.addObject("Part::Feature",self.name+"_Miter")
            obj.Shape = self.miter
            obj.ViewObject.ShapeColor=(1.0, 0.0, 0.0)
        except Exception  as e:
            doc.removeObject(obj.Label)            
    def __wall(self,side):
        #print("*** GreenHouse.__wall(",self,",",side,")")
        if side=='Front':
            norm=Base.Vector(0,1,0)
            extrude=Base.Vector(0,self.__wallThickness,0)
            extrudeIndent=Base.Vector(0,self.__wallIndent,0)
            wallOrigin = self.origin
            width = self.__length+self.__wallThickness
            miter1Origin=Base.Vector(width-self.__wallThickness,
                                     self.__wallThickness,
                                     self.__wallHeight)
            miter1Norm=Base.Vector(1,1,0)
            miter1extrude=Base.Vector(self.__wallThickness,
                                      self.__wallThickness,0)
            miter2Origin=None
        elif side=='Right':
            norm=Base.Vector(1,0,0)
            extrude=Base.Vector(self.__wallThickness,0,0)
            extrudeIndent=Base.Vector(self.__wallIndent,0,0)
            wallOrigin = self.origin.add(Base.Vector(self.__length,self.__width,0))
            width = self.__width
            miter1Origin=Base.Vector(self.__wallThickness,
                                     -self.__width,
                                     self.__wallHeight)
            miter1Norm=Base.Vector(-1,-1,0)
            miter1extrude=Base.Vector(-self.__wallThickness,
                                      -self.__wallThickness,0)
            miter2Origin=Base.Vector(self.__wallThickness,
                                     0,
                                     self.__wallHeight)
            miter2Norm=Base.Vector(-1,-1,0)
            miter2extrude=Base.Vector(-self.__wallThickness,
                                      -self.__wallThickness,0)
        elif side=='Rear':
            norm=Base.Vector(0,-1,0)
            extrude=Base.Vector(0,-self.__wallThickness,0)
            extrudeIndent=Base.Vector(0,-self.__wallIndent,0)
            wallOrigin = self.origin.add(Base.Vector(0,
                                                     self.__width,
                                                     self.__wallHeight))
            width = self.__length+self.__wallThickness
            miter1Origin=Base.Vector(width-self.__wallThickness,
                                     -self.__wallThickness,
                                     0)
            miter1Norm=Base.Vector(1,1,0)
            miter1extrude=Base.Vector(self.__wallThickness,
                                      self.__wallThickness,0)
            miter2Origin=None
        else:
            raise RuntimeError("unsuported side!")
        wall = Part.makePlane(self.__wallHeight,
                              width,
                              wallOrigin,
                              norm).extrude(extrude)
        if miter1Origin != None:
            miter = Part.makePlane(self.__wallThickness*2,
                                   self.__wallHeight,
                                   wallOrigin.add(miter1Origin),
                                   miter1Norm).extrude(miter1extrude)
            wall = wall.cut(miter)
            #self.miter = miter
        if miter2Origin != None:
            miter = Part.makePlane(self.__wallThickness*2,
                                   self.__wallHeight,
                                   wallOrigin.add(miter2Origin),
                                   miter2Norm).extrude(miter2extrude)
            wall = wall.cut(miter)
            #self.miter = miter
        for window in range(0,2):
            #print("*** -: window is ",window)
            if side=='Front':
                windowOrigin = wallOrigin.add(
                    Base.Vector(self.__windowOffset+
                                    (window*self.__window2Offset),
                                0,self.__windowBottom))
                w =  Part.makePlane(self.__windowHeight,
                                    self.__windowWidth,
                                    windowOrigin,
                                    norm).extrude(extrude)
                wIndent =  Part.makePlane(self.__windowHeight+
                                          self.__upperWindowOffset,
                                    self.__windowWidth,
                                    windowOrigin,
                                    norm).extrude(extrudeIndent)
                wall = wall.cut(w)
                for py in range(1,10):
                    bar = Part.makePlane(self.__windowBarWidth,
                                         self.__windowWidth,
                                         windowOrigin.add(
                                            Base.Vector(0,0,
                                                py*self.__windowPaneZStride)),
                    norm).extrude(extrude)
                    wall = wall.fuse(bar)
                for px in range(1,10):
                    bar = Part.makePlane(self.__windowHeight,
                                         self.__windowBarWidth,
                                         windowOrigin.add(
                                            Base.Vector(px*self.__windowPaneXStride,
                                                        0,0)),norm).extrude(extrude)
                    #self.miter = bar
                    wall = wall.fuse(bar)
                windowCenter = windowOrigin.add(
                        Base.Vector(self.__windowWidth/2,0,
                                    self.__windowHeight +
                                    self.__upperWindowOffset))
                upperWindowArcC = Part.makeCircle(self.__upperWindowRadius,
                                                 windowCenter,norm,
                                                 180,360)
                upperWindowArcL = Part.makeLine(
                  windowCenter.add(Base.Vector(-self.__upperWindowRadius,0,0)),
                  windowCenter.add(Base.Vector(self.__upperWindowRadius,0,0)))
                upperWindowArc=Part.Face(Part.Wire([upperWindowArcC,
                                                    upperWindowArcL])
                                        ).extrude(extrude)
                upperWindowArcIndent = Part.Face(Part.Wire([upperWindowArcC,
                                                            upperWindowArcL])
                                        ).extrude(extrudeIndent)
                wIndent = wIndent.fuse(upperWindowArcIndent)
                wall = wall.cut(upperWindowArc)
                for b in range(1,8):
                    #print("*** -: b is ",b)
                    bangle = math.radians((b*self.__upperBarAngle))
                    bangleCOS = math.cos(bangle)
                    bangleSIN = math.sin(bangle)
                    bangleCOS_M = math.cos(bangle+math.pi)
                    bangleSIN_M = math.sin(bangle+math.pi)
                    #print("*** -: bangleCOS is ",bangleCOS)
                    #print("*** -: bangleSIN is ",bangleSIN)
                    #print("*** -: bangleCOS_M is ",bangleCOS_M)
                    #print("*** -: bangleSIN_M is ",bangleSIN_M)
                    p = Base.Vector(self.__upperWindowRadius*bangleCOS,
                                    0,
                                    self.__upperWindowRadius*bangleSIN)
                    barPoly = list()
                    p1 = p.add(Base.Vector(self.__upperBarWidth*
                                                bangleSIN_M,
                                           0,
                                           self.__upperBarWidth*
                                                bangleCOS))
                    p0 = p1
                    barPoly.append(windowCenter.add(p1))
                    p1 = p.add(Base.Vector(self.__upperBarWidth*
                                                bangleSIN,
                                           0,
                                           self.__upperBarWidth*
                                                bangleCOS_M))
                    barPoly.append(windowCenter.add(p1))
                    p1 = Base.Vector(self.__upperBarWidth*bangleSIN,
                                     0,
                                     self.__upperBarWidth*bangleCOS_M)
                    barPoly.append(windowCenter.add(p1))
                    p1 = Base.Vector(self.__upperBarWidth*bangleSIN_M,
                                     0,
                                     self.__upperBarWidth*bangleCOS)
                    barPoly.append(windowCenter.add(p1))
                    barPoly.append(windowCenter.add(p0))
                    #print("*** -: barPoly is ",barPoly)
                    try:
                        bar = Part.Face(Part.Wire(Part.makePolygon(barPoly))
                                        ).extrude(extrude)
                        
                        wall = wall.fuse(bar)
                    except Part.OCCError as e:
                        #print("*** GreenHouse.__wall(): bangle is ",bangle)
                        #print("*** GreenHouse.__wall(): p is ",p)
                        #print("*** GreenHouse.__wall(): barPoly is ",barPoly)
                        #print("*** GreenHouse.__wall(): Failed to create face from wire")
                        pass
                #self.miter = upperWindowArcIndent
                wall = wall.cut(wIndent)
            elif side=='Right':
                windowOrigin = wallOrigin.add(
                    Base.Vector(0,-(self.__windowOffset+
                                    (window*self.__window2Offset)),
                                self.__windowBottom))
                w =  Part.makePlane(self.__windowHeight,
                                    self.__windowWidth,
                                    windowOrigin,
                                    norm).extrude(extrude)
                wIndent =  Part.makePlane(self.__windowHeight+
                                          self.__upperWindowOffset,
                                    self.__windowWidth,
                                    windowOrigin.add(
                                        Base.Vector(self.__wallIndent,0,0)),
                                    norm).extrude(extrudeIndent)
                #self.miter = wIndent
                wall = wall.cut(w)
                for py in range(1,10):
                    bar = Part.makePlane(self.__windowBarWidth,
                                         self.__windowWidth,
                                         windowOrigin.add(
                                            Base.Vector(0,0,
                                                        py*self.__windowPaneZStride)),
                                         norm).extrude(extrude)
                    wall = wall.fuse(bar)
                for px in range(1,10):
                    bar = Part.makePlane(self.__windowHeight,
                                         self.__windowBarWidth,
                                         windowOrigin.add(
                                                Base.Vector (0,
                                                             -px*self.__windowPaneXStride,
                                                             0)),
                                         norm).extrude(extrude)
                    wall = wall.fuse(bar)
                windowCenter = windowOrigin.add(
                        Base.Vector(0,-self.__windowWidth/2,
                                    self.__windowHeight +
                                    self.__upperWindowOffset))
                upperWindowArcC = Part.makeCircle(self.__upperWindowRadius,
                                                 windowCenter,norm,
                                                 0,180)
                upperWindowArcL = Part.makeLine(
                  windowCenter.add(Base.Vector(0,-self.__upperWindowRadius,0)),
                  windowCenter.add(Base.Vector(0,self.__upperWindowRadius,0)))
                upperWindowArc=Part.Face(Part.Wire([upperWindowArcC,
                                                    upperWindowArcL])
                                        ).extrude(extrude)
                upperWindowArcCI = Part.makeCircle(self.__upperWindowRadius,
                                                 windowCenter.add(
                                                    Base.Vector(
                                                        self.__wallIndent,
                                                        0,0)),
                                                 norm,
                                                 0,180)
                upperWindowArcLI = Part.makeLine(
                  windowCenter.add(Base.Vector(self.__wallIndent,
                                               -self.__upperWindowRadius,0)),
                  windowCenter.add(Base.Vector(self.__wallIndent,
                                               self.__upperWindowRadius,0)))
                upperWindowArcIndent=Part.Face(Part.Wire([upperWindowArcCI,
                                                    upperWindowArcLI])
                                        ).extrude(extrudeIndent)
                wIndent = wIndent.fuse(upperWindowArcIndent)
                wall = wall.cut(upperWindowArc)
                for b in range(1,8):
                    #print("*** -: b is ",b)
                    bangle = math.radians((b*self.__upperBarAngle))
                    bangleCOS = math.cos(bangle)
                    bangleSIN = math.sin(bangle)
                    bangleCOS_M = math.cos(bangle+math.pi)
                    bangleSIN_M = math.sin(bangle+math.pi)
                    #print("*** -: bangleCOS is ",bangleCOS)
                    #print("*** -: bangleSIN is ",bangleSIN)
                    #print("*** -: bangleCOS_M is ",bangleCOS_M)
                    #print("*** -: bangleSIN_M is ",bangleSIN_M)
                    p = Base.Vector(0,self.__upperWindowRadius*bangleCOS,
                                    self.__upperWindowRadius*bangleSIN)
                    barPoly = list()
                    p1 = p.add(Base.Vector(0,self.__upperBarWidth*
                                                bangleSIN_M,
                                           self.__upperBarWidth*
                                                bangleCOS))
                    p0 = p1
                    barPoly.append(windowCenter.add(p1))
                    p1 = p.add(Base.Vector(0,self.__upperBarWidth*
                                                bangleSIN,
                                           self.__upperBarWidth*
                                                bangleCOS_M))
                    barPoly.append(windowCenter.add(p1))
                    p1 = Base.Vector(0,self.__upperBarWidth*bangleSIN,
                                     self.__upperBarWidth*bangleCOS_M)
                    barPoly.append(windowCenter.add(p1))
                    p1 = Base.Vector(0,self.__upperBarWidth*bangleSIN_M,
                                     self.__upperBarWidth*bangleCOS)
                    barPoly.append(windowCenter.add(p1))
                    barPoly.append(windowCenter.add(p0))
                    #print("*** -: barPoly is ",barPoly)
                    try:
                        bar = Part.Face(Part.Wire(Part.makePolygon(barPoly))
                                        ).extrude(extrude)
                        
                        wall = wall.fuse(bar)
                    except Part.OCCError as e:
                        #print("*** GreenHouse.__wall(): bangle is ",bangle)
                        #print("*** GreenHouse.__wall(): p is ",p)
                        #print("*** GreenHouse.__wall(): barPoly is ",barPoly)
                        #print("*** GreenHouse.__wall(): Failed to create face from wire")
                        pass
                #self.miter = bar
                wall = wall.cut(wIndent)
            elif side=='Rear':
                windowOrigin = wallOrigin.add(
                    Base.Vector((self.__windowOffset+
                                    (window*self.__window2Offset)),
                                0,-(self.__wallHeight-
                                    self.__windowHeight-
                                    self.__windowBottom)))
                w =  Part.makePlane(self.__windowHeight,
                                    self.__windowWidth, 
                                    windowOrigin,
                                    norm).extrude(extrude)
                wIndent =  Part.makePlane(self.__windowHeight+
                                          self.__upperWindowOffset,
                                    self.__windowWidth, 
                                    windowOrigin.add(
                                        Base.Vector(0,0,
                                                    self.__upperWindowOffset)),
                                    norm).extrude(extrudeIndent)
                wall = wall.cut(w)
                for py in range(1,10):
                    bar = Part.makePlane(self.__windowBarWidth,
                                         self.__windowWidth,
                                         windowOrigin.add(
                                            Base.Vector(0,0,
                                                        -((py*self.__windowPaneZStride)+
                                                          self.__windowBarWidth*2))),
                                         norm).extrude(extrude)
                    wall = wall.fuse(bar)
                for px in range(1,10):
                    bar = Part.makePlane(self.__windowHeight,
                                         self.__windowBarWidth,
                                         windowOrigin.add(
                                            Base.Vector(px*self.__windowPaneXStride,
                                            0,0)),
                                         norm).extrude(extrude)
                    wall = wall.fuse(bar)
                windowCenter = windowOrigin.add(
                        Base.Vector(self.__windowWidth/2,0,
                                    self.__upperWindowOffset))
                upperWindowArcC = Part.makeCircle(self.__upperWindowRadius,
                                                 windowCenter,norm,
                                                 0,180)
                upperWindowArcL = Part.makeLine(
                  windowCenter.add(Base.Vector(-self.__upperWindowRadius,0,0)),
                  windowCenter.add(Base.Vector(self.__upperWindowRadius,0,0)))
                upperWindowArc=Part.Face(Part.Wire([upperWindowArcC,
                                                    upperWindowArcL])
                                        ).extrude(extrude)
                upperWindowArcIndent = Part.Face(Part.Wire([upperWindowArcC,
                                                            upperWindowArcL])
                                        ).extrude(extrudeIndent)
                wIndent = wIndent.fuse(upperWindowArcIndent)
                #self.miter = upperWindowArc
                wall = wall.cut(upperWindowArc)
                for b in range(1,8):
                    #print("*** -: b is ",b)
                    bangle = math.radians((b*self.__upperBarAngle))
                    bangleCOS = math.cos(bangle)
                    bangleSIN = math.sin(bangle)
                    bangleCOS_M = math.cos(bangle+math.pi)
                    bangleSIN_M = math.sin(bangle+math.pi)
                    #print("*** -: bangleCOS is ",bangleCOS)
                    #print("*** -: bangleSIN is ",bangleSIN)
                    #print("*** -: bangleCOS_M is ",bangleCOS_M)
                    #print("*** -: bangleSIN_M is ",bangleSIN_M)
                    p = Base.Vector(self.__upperWindowRadius*bangleCOS,
                                    0,
                                    self.__upperWindowRadius*bangleSIN)
                    barPoly = list()
                    p1 = p.add(Base.Vector(self.__upperBarWidth*
                                                bangleSIN_M,
                                           0,
                                           self.__upperBarWidth*
                                                bangleCOS))
                    p0 = p1
                    barPoly.append(windowCenter.add(p1))
                    p1 = p.add(Base.Vector(self.__upperBarWidth*
                                                bangleSIN,
                                           0,
                                           self.__upperBarWidth*
                                                bangleCOS_M))
                    barPoly.append(windowCenter.add(p1))
                    p1 = Base.Vector(self.__upperBarWidth*bangleSIN,
                                     0,
                                     self.__upperBarWidth*bangleCOS_M)
                    barPoly.append(windowCenter.add(p1))
                    p1 = Base.Vector(self.__upperBarWidth*bangleSIN_M,
                                     0,
                                     self.__upperBarWidth*bangleCOS)
                    barPoly.append(windowCenter.add(p1))
                    barPoly.append(windowCenter.add(p0))
                    #print("*** -: barPoly is ",barPoly)
                    try:
                        bar = Part.Face(Part.Wire(Part.makePolygon(barPoly))
                                        ).extrude(extrude)
                        
                        wall = wall.fuse(bar)
                    except Part.OCCError as e:
                        #print("*** GreenHouse.__wall(): bangle is ",bangle)
                        #print("*** GreenHouse.__wall(): p is ",p)
                        #print("*** GreenHouse.__wall(): barPoly is ",barPoly)
                        #print("*** GreenHouse.__wall(): Failed to create face from wire")
                        pass
                #self.miter = bar
                wall = wall.cut(wIndent)
            else:
                raise RuntimeError("unsuported side!")
        return(wall)
    def __roof(self):
        roof = Mesh.read(self.__roofSTL)
        #Vector (153.82313537597656, 105.96363830566406, 91.41316986083984)
        roof.translate(-153.82313537597656, -105.96363830566406, -91.41316986083984)
        roof.rotate(math.pi/2,0,0)
        ro = self.origin.add(self.__roofOrigin)
        roof.translate(ro.x,ro.y,ro.z)
        return(roof)

class RoofSection(BirchPanel, InstanceIter):
    # Overhang points:
    # Vector (-291.2991943359375, 191.2957000732422, 162.26939392089844)
    # Vector (-287.65008544921875, 191.39491271972656, 159.75738525390625)
    # Vector (-322.970458984375, 200.30540466308594, 202.69088745117188)
    __overhangThickness = (1/8)*25.4
    __overhangWidth = 80
    __overhangWallOverlap = (1/8)*25.4
    OverhangOffset = 31-((1/8)*25.4)
    # Roof points:
    # Vector (-297.5604553222656, 200.30540466308594, 171.80958557128906)
    # Vector (-280.6936340332031, 278.30072021484375, 133.6685791015625)
    __slopeDX = -280.6936340332031 - -297.5604553222656
    __slopeDY = 171.80958557128906 - 133.6685791015625
    @property
    def __slopeDXY(self):
        return (self.__slopeDX+self.__slopeDY)/2
    __slopeDZ = 278.30072021484375 - 200.30540466308594
    __roofSetBack = 202.69088745117188-171.80958557128906
    @property
    def __roofSlopeFrontNormal(self):
        theta = math.atan2(self.__slopeDXY,self.__slopeDZ)+math.pi
        return Base.Vector(0,-math.cos(theta),math.sin(theta))
    @property
    def __roofSlopeFrontExtrude(self):
        return self.__roofSlopeFrontNormal*BirchPanel.Thickness()
    @property
    def __roofSlopeWidth(self):
        return math.hypot(self.__slopeDXY,self.__slopeDZ)
    @property
    def __roofSlopeRearNormal(self):
        theta = math.atan2(self.__slopeDXY,self.__slopeDZ)
        return Base.Vector(0,math.cos(theta),math.sin(theta))
    @property
    def __roofSlopeRearExtrude(self):
        return self.__roofSlopeRearNormal*BirchPanel.Thickness()
    @property
    def __roofSlopeRightNormal(self):
        theta = math.atan2(self.__slopeDXY,self.__slopeDZ)
        return Base.Vector(math.cos(theta),0,math.sin(theta))
    @property
    def __roofSlopeRightExtrude(self):
        return self.__roofSlopeRightNormal*BirchPanel.Thickness()
    @property
    def __roofSlopeLeftNormal(self):
        theta = math.atan2(self.__slopeDXY,self.__slopeDZ)
        return Base.Vector(math.cos(theta),0,-math.sin(theta))
    @property
    def __roofSlopeLeftExtrude(self):
        return self.__roofSlopeLeftNormal*BirchPanel.Thickness()
    # Roof fence points:
    # Vector (-275.3706970214844, 278.30072021484375, 128.3632049560547)
    # Vector (-275.3706970214844, 301.8320617675781, 128.3293914794922)
    __fenceSetback = 5.3229370117187
    __fenceHelght = 301.8320617675781-278.30072021484375
    def __str__(self):
        try:
            result = '<RoofSection name="'+self.name+'"'
            result = result+', origin='+str(self.origin)
            result = result+', side="'+self.side+'">'
            return result
        except BaseException:
            return "<RoofSection>"
    def __init__(self,name,origin,length,*,braces=[],side='Front',
                 start='Square',end='Square'):
        super(RoofSection,self).__init__()
        self.name = name
        if not isinstance(origin,Base.Vector):
            raise RuntimeError("origin is not a Vector!")
        self.origin = origin
        self.side = side
        miterCutStart = None
        miterCutEnd   = None
        if side == 'Front':
            roofnorm = self.__roofSlopeFrontNormal
            roofH = length
            roofW = self.__roofSlopeWidth
            slopeextrude = self.__roofSlopeFrontExtrude
            overhangH = length
            overhangW = self.__overhangWidth
            roofOrigin = self.origin.add(
                        Base.Vector(0,
                                    self.__roofSetBack,
                                    self.__overhangThickness))
            if len(braces) > 0:
                bracenorm = Base.Vector(1,0,0)
                braceextrude = bracenorm*BirchPanel.Thickness()
                braceCutExtrude = slopeextrude*-self.__slopeDXY
                braceCut = Part.makePlane(roofW+BirchPanel.Thickness(),
                                          roofH,
                                          roofOrigin.add(
                                            Base.Vector(0,
                                                BirchPanel.Thickness()-1.2,
                                                -BirchPanel.Thickness())),
                                          roofnorm).extrude(braceCutExtrude)
                braceOrigins = list()
                braceH = self.__overhangWidth-self.__roofSetBack
                braceW = self.__slopeDZ-BirchPanel.Thickness()
                for b in braces:
                    braceOrigins.append(self.origin.add( 
                                Base.Vector(b,
                                            self.__overhangWidth,
                                            self.__overhangThickness)))
            if start=='Square':
                pass
            elif start=='InnerMiter':
                mheight = self.__slopeDZ+self.__overhangThickness
                mwidth = self.__overhangWidth+self.__overhangThickness*2
                miterOrigin=self.origin.add(
                        Base.Vector(0,
                                    mwidth-self.__overhangThickness*2,
                                    mwidth))
                miterNorm=Base.Vector(1,-1,0)
                miterExtrude=miterNorm*self.__overhangWidth
                miterCutStart = Part.makePlane(mheight,
                                               mwidth,
                                               miterOrigin,
                                               miterNorm).extrude(miterExtrude)
            elif start=='OuterMiter':
                mheight = self.__slopeDZ+self.__overhangThickness
                mwidth = self.__overhangWidth+self.__overhangThickness*2
                miterOrigin=self.origin.add(
                        Base.Vector(mheight,
                                    mwidth-self.__overhangThickness*2,
                                    mwidth))
                miterNorm=Base.Vector(-1,-1,0)
                miterExtrude=miterNorm*mheight
                miterCutStart = Part.makePlane(mheight,
                                               mwidth,
                                               miterOrigin,
                                               miterNorm).extrude(miterExtrude)
            else:
                raise RuntimeError("Unsupported Miter")
            if end=='Square':
                pass
            elif end=='InnerMiter':
                mheight = self.__slopeDZ+self.__overhangThickness
                mwidth = self.__overhangWidth+self.__overhangThickness*2
                miterOrigin=self.origin.add(
                        Base.Vector(length-mheight+self.__overhangThickness-2,
                                    0,
                                    mwidth))
                miterNorm=Base.Vector(1,1,0)
                miterExtrude=miterNorm*self.__overhangWidth
                miterCutEnd = Part.makePlane(mheight,
                                               mwidth,
                                               miterOrigin,
                                               miterNorm).extrude(miterExtrude)
            elif end=='OuterMiter':
                mheight = self.__slopeDZ+self.__overhangThickness
                mwidth = self.__overhangWidth+self.__overhangThickness*2
                miterOrigin=self.origin.add(
                        Base.Vector(length-mheight+1.2,
                                    mwidth-self.__overhangThickness*2,
                                    mwidth))
                miterNorm=Base.Vector(-1,1,0)
                miterExtrude=miterNorm*-mheight
                miterCutEnd = Part.makePlane(mheight,
                                               mwidth,
                                               miterOrigin,
                                               miterNorm).extrude(miterExtrude)
            else:
                raise RuntimeError("Unsupported Miter")
        elif side == 'Left':
            roofnorm = self.__roofSlopeLeftNormal
            roofW = self.__roofSlopeWidth
            roofH = length
            slopeextrude = self.__roofSlopeLeftExtrude
            overhangH = self.__overhangWidth
            overhangW = length
            roofOrigin = self.origin.add(
                        Base.Vector(self.__roofSetBack,length,
                                    self.__overhangThickness))
            if len(braces) > 0:
                bracenorm = Base.Vector(0,-1,0)
                braceextrude = bracenorm*BirchPanel.Thickness()
                braceCutExtrude = slopeextrude*-self.__slopeDXY
                braceCut = Part.makePlane(roofW+BirchPanel.Thickness(),
                                          roofH,
                                          roofOrigin.add(
                                            Base.Vector(BirchPanel.Thickness()-
                                                 .62,
                                                 0,
                                                -BirchPanel.Thickness())),
                                          roofnorm).extrude(braceCutExtrude)
                #self.braceCut = braceCut
                braceOrigins = list()
                braceH = self.__overhangWidth-self.__roofSetBack
                braceW = self.__slopeDZ-BirchPanel.Thickness()
                for b in braces:
                    braceOrigins.append(self.origin.add( 
                                Base.Vector(self.__roofSetBack,
                                            b,
                                            self.__overhangThickness+braceW)))
            if start=='Square':
                pass
            elif start=='InnerMiter':
                mheight = self.__slopeDZ+self.__overhangThickness
                mwidth = self.__overhangWidth+self.__overhangThickness*2
                miterOrigin=self.origin.add(
                        Base.Vector(0,
                                    mwidth-self.__overhangThickness*2,
                                    mwidth))
                miterNorm=Base.Vector(1,-1,0)
                miterExtrude=miterNorm*self.__overhangWidth
                miterCutStart = Part.makePlane(mheight,
                                               mwidth,
                                               miterOrigin,
                                               miterNorm).extrude(miterExtrude)
            elif start=='OuterMiter':
                mheight = self.__slopeDZ+self.__overhangThickness
                mwidth = self.__overhangWidth+self.__overhangThickness*2
                miterOrigin=self.origin.add(
                        Base.Vector(mheight+
                                    self.__overhangWidth-
                                    self.__roofSetBack+
                                    self.__overhangThickness*2.5,
                                    23.5, 
                                    mwidth))
                miterNorm=Base.Vector(-1,-1,0)
                miterExtrude=miterNorm*mheight
                miterCutStart = Part.makePlane(mheight,
                                               mwidth,
                                               miterOrigin,
                                               miterNorm).extrude(miterExtrude)
            else:
                raise RuntimeError("Unsupported Miter")
            if end=='Square':
                pass
            elif end=='InnerMiter':
                mheight = self.__slopeDZ+self.__overhangThickness
                mwidth = self.__overhangWidth+self.__overhangThickness*2
                miterOrigin=self.origin.add(
                        Base.Vector(-57.44,
                                    length-22.6,
                                    mwidth))
                miterNorm=Base.Vector(1,1,0)
                miterExtrude=miterNorm*self.__overhangWidth
                miterCutEnd = Part.makePlane(mheight,
                                               mwidth,
                                               miterOrigin,
                                               miterNorm).extrude(miterExtrude)
            elif end=='OuterMiter':
                mheight = self.__slopeDZ+self.__overhangThickness
                mwidth = self.__overhangWidth+self.__overhangThickness*2
                miterOrigin=self.origin.add(
                        Base.Vector(0,
                                    length,#-mheight+1.2,
                                    mwidth))
                miterNorm=Base.Vector(-1,1,0)
                miterExtrude=miterNorm*-mheight
                miterCutEnd = Part.makePlane(mheight,
                                               mwidth,
                                               miterOrigin,
                                               miterNorm).extrude(miterExtrude)
            else:
                raise RuntimeError("Unsupported Miter")
        elif side == 'Right':
            roofnorm = self.__roofSlopeRightNormal
            roofW = self.__roofSlopeWidth
            roofH = length
            slopeextrude = self.__roofSlopeRightExtrude
            overhangH = self.__overhangWidth
            overhangW = length
            roofOrigin = self.origin.add(
                        Base.Vector(self.__overhangWidth-(
                                        self.__roofSetBack+
                                        self.__overhangThickness),
                                    length,
                                   self.__overhangThickness-.68))
            if len(braces) > 0:
                bracenorm = Base.Vector(0,1,0)
                braceextrude = bracenorm*BirchPanel.Thickness()
                braceCutExtrude = slopeextrude*self.__slopeDXY
                braceCut = Part.makePlane(roofW+BirchPanel.Thickness(),
                                          roofH,
                                          roofOrigin.add(
                                            Base.Vector(0,
                                                BirchPanel.Thickness(),
                                                0)),
                                          roofnorm).extrude(braceCutExtrude)
                braceOrigins = list()
                braceH = self.__overhangWidth-self.__roofSetBack
                braceW = self.__slopeDZ-BirchPanel.Thickness()
                for b in braces:
                    braceOrigins.append(self.origin.add( 
                                Base.Vector(0,
                                            b,
                                            BirchPanel.Thickness())))
            if start=='Square':
                pass
            elif start=='InnerMiter':
                mheight = self.__slopeDZ+self.__overhangThickness
                mwidth = self.__overhangWidth+self.__overhangThickness*2
                miterOrigin=self.origin.add(
                        Base.Vector(mheight+
                                    self.__overhangWidth-
                                    self.__roofSetBack+
                                    self.__overhangThickness*2.5,
                                    23.5, 
                                    mwidth))
                miterNorm=Base.Vector(-1,-1,0)
                miterExtrude=miterNorm*mheight
                miterCutStart = Part.makePlane(mheight,
                                               mwidth,
                                               miterOrigin,
                                               miterNorm).extrude(miterExtrude)
            elif start=='OuterMiter':
                mheight = self.__slopeDZ+self.__overhangThickness
                mwidth = self.__overhangWidth+self.__overhangThickness*2
                miterOrigin=self.origin.add(
                        Base.Vector(0,
                                    81.17, 
                                    mwidth))
                miterNorm=Base.Vector(1,-1,0)
                miterExtrude=miterNorm*mheight
                miterCutStart = Part.makePlane(mheight,
                                               mwidth,
                                               miterOrigin,
                                               miterNorm).extrude(miterExtrude)
            else:
                raise RuntimeError("Unsupported Miter")
            if end=='Square':
                pass
            elif end=='InnerMiter':
                mheight = self.__slopeDZ+self.__overhangThickness
                mwidth = self.__overhangWidth+self.__overhangThickness*2
                miterOrigin=self.origin.add(
                        Base.Vector(57.4,
                                    length+57.4, 
                                    mwidth))
                miterNorm=Base.Vector(1,-1,0)
                miterExtrude=miterNorm*mheight
                miterCutEnd = Part.makePlane(mheight,
                                               mwidth,
                                               miterOrigin,
                                               miterNorm).extrude(miterExtrude)
            elif end=='OuterMiter':
                mheight = self.__slopeDZ+self.__overhangThickness
                mwidth = self.__overhangWidth+self.__overhangThickness*2
                miterOrigin=self.origin.add(
                        Base.Vector(self.__overhangWidth,
                                    length, 
                                    mwidth))
                miterNorm=Base.Vector(-1,-1,0)
                miterExtrude=miterNorm*mheight
                miterCutEnd = Part.makePlane(mheight,
                                               mwidth,
                                               miterOrigin,
                                               miterNorm).extrude(miterExtrude)
            else:
                raise RuntimeError("Unsupported Miter")
            #self.miter = miterCutEnd
        elif side == 'Rear':
            roofnorm = self.__roofSlopeRearNormal
            roofH = length
            roofW = self.__roofSlopeWidth
            slopeextrude = self.__roofSlopeRearExtrude
            overhangH = length
            overhangW = self.__overhangWidth
            roofOrigin = self.origin.add(
                        Base.Vector(0,self.__overhangWidth-self.__roofSetBack-
                                    self.__overhangThickness,
                                    self.__overhangThickness*.5))
            if len(braces) > 0:
                bracenorm = Base.Vector(-1,0,0)
                braceextrude = bracenorm*BirchPanel.Thickness()
                braceCutExtrude = slopeextrude*self.__slopeDXY
                braceCut = Part.makePlane(roofW+BirchPanel.Thickness(),
                                          roofH,
                                          roofOrigin.add(
                                            Base.Vector(0,
                                                BirchPanel.Thickness()-1.2,
                                                -BirchPanel.Thickness())),
                                          roofnorm).extrude(braceCutExtrude)
                braceOrigins = list()
                braceH = self.__overhangWidth-self.__roofSetBack
                braceW = self.__slopeDZ-BirchPanel.Thickness()
                for b in braces:
                    braceOrigins.append(self.origin.add( 
                                Base.Vector(b,
                                            braceH,
                                            self.__overhangThickness+braceW)))
            if start=='Square':
                pass
            elif start=='InnerMiter':
                mheight = self.__slopeDZ+self.__overhangThickness
                mwidth = self.__overhangWidth+self.__overhangThickness*2
                miterOrigin=self.origin.add(
                        Base.Vector(self.__overhangWidth,
                                    mwidth-self.__overhangThickness*2,
                                    mwidth))
                miterNorm=Base.Vector(-1,-1,0)
                miterExtrude=miterNorm*self.__overhangWidth
                miterCutStart = Part.makePlane(mheight,
                                               mwidth,
                                               miterOrigin,
                                               miterNorm).extrude(miterExtrude)
            elif start=='OuterMiter':
                mheight = self.__slopeDZ+self.__overhangThickness
                mwidth = self.__overhangWidth+self.__overhangThickness*2
                miterOrigin=self.origin.add(
                        Base.Vector(23.77,
                                    -57.4,
                                    mwidth))
                miterNorm=Base.Vector(-1,1,0)
                miterExtrude=miterNorm*mheight
                miterCutStart = Part.makePlane(mheight,
                                               mwidth,
                                               miterOrigin,
                                               miterNorm).extrude(miterExtrude)
            else:
                raise RuntimeError("Unsupported Miter")
            if end=='Square':
                pass
            elif end=='InnerMiter':
                mheight = self.__slopeDZ+self.__overhangThickness
                mwidth = self.__overhangWidth+self.__overhangThickness*2
                miterOrigin=self.origin.add(
                        Base.Vector(length-mheight+1.2,
                                    mwidth-self.__overhangThickness*2,
                                    mwidth))
                miterNorm=Base.Vector(-1,1,0)
                miterExtrude=miterNorm*-mheight
                miterCutEnd = Part.makePlane(mheight,
                                               mwidth,
                                               miterOrigin,
                                               miterNorm).extrude(miterExtrude)
            elif end=='OuterMiter':
                mheight = self.__slopeDZ+self.__overhangThickness
                mwidth = self.__overhangWidth+self.__overhangThickness*2
                miterOrigin=self.origin.add(
                        Base.Vector(length-mheight+self.__overhangThickness-2,
                                    0,
                                    mwidth))
                miterNorm=Base.Vector(1,1,0)
                miterExtrude=miterNorm*self.__overhangWidth
                miterCutEnd = Part.makePlane(mheight,
                                               mwidth,
                                               miterOrigin,
                                               miterNorm).extrude(miterExtrude)
            else:
                raise RuntimeError("Unsupported Miter")
        else:
            raise RuntimeError("unsuported side!")
        self.overhang = Part.makePlane(overhangH,
                                       overhangW,
                                       self.origin
                                      ).extrude(
                                     Base.Vector(0,0,self.__overhangThickness))
        self.roofpanel = Part.makePlane(roofW,
                                        roofH,
                                        roofOrigin,
                                        roofnorm).extrude(slopeextrude)
        self.roofnorm = roofnorm
        self.roofLength = length
        self.braces = list()
        self.bracenorm = bracenorm
        if len(braces) > 0:
            for b in braceOrigins:
                brace = Part.makePlane(braceW,
                                       braceH,
                                       b,
                                       bracenorm).extrude(braceextrude)
                self.braces.append(brace.cut(braceCut))
        if miterCutStart != None:
            self.overhang = self.overhang.cut(miterCutStart)
            self.roofpanel = self.roofpanel.cut(miterCutStart)
        if miterCutEnd != None:
            self.overhang = self.overhang.cut(miterCutEnd)
            self.roofpanel = self.roofpanel.cut(miterCutEnd)
        self.panelPage = 0
        self.techDoc = None
    def sortKey(self):
        return self.roofLength
    def show(self,doc=None):
        if doc==None:
            doc = App.activeDocument()
        obj = doc.addObject("Part::Feature",self.name+"_Overhang")
        obj.Shape = self.overhang
        obj.Label=self.name+"_Overhang"
        obj.ViewObject.ShapeColor=self.Color
        obj = doc.addObject("Part::Feature",self.name+"_Roof")
        obj.Shape = self.roofpanel
        obj.Label=self.name+"_Roof"
        obj.ViewObject.ShapeColor=self.Color
        for i,b in enumerate(self.braces):
            n = self.name+"_Brace%02d"%(i)
            obj = doc.addObject("Part::Feature",n)
            obj.Shape = b
            obj.Label = n
            obj.ViewObject.ShapeColor=self.Color
        try:
            obj = doc.addObject("Part::Feature","Miter")
            obj.Shape = self.miter
            obj.ViewObject.ShapeColor=(1.0, 0.0, 0.0)
        except AttributeError as e:
            doc.removeObject(obj.Label)
    def PanelPage(self,techDoc,page,lastX,lastY,deltaY,*,minX=50,minY=50,
                                             maxX=(24*25.4)-50,
                                             maxY=(16*25.4)-50):
        if techDoc != self.techDoc:
            self.panelPage = 0;
            self.techDoc = techDoc
        while self.panelPage < (len(self.braces) + 2):
            if self.panelPage == 0:
                bbox = self.overhang.BoundBox
                lengthX = bbox.XLength
                lengthY = bbox.YLength
                fitP, currentX, currentY, lengthX, lengthY, deltaY, rotation =\
                    BirchPanel.FitPanel(page,lastX,lastY,lengthX,lengthY,deltaY,
                                        minX,minY,maxX,maxY)
                if not fitP:
                    return (True, -1, -1, deltaY)
                obj = techDoc.addObject("Part::Feature",self.name+"_Overhang")
                obj.Shape = self.overhang
                obj.ViewObject.Visibility = False
                panel = techDoc.addObject('TechDraw::DrawViewPart',self.name+"_Overhang_View")
                page.addView(panel)
                panel.Source = obj 
                panel.X = currentX+lengthX/2
                panel.Y = currentY+lengthY/2
                panel.Rotation = rotation
                panel.Direction = (0,0,1)
                lastX = currentX+lengthX+10
                lastY = currentY
                self.panelPage += 1
            elif self.panelPage == 1:
                # roof panel
                if self.roofnorm.y == 0:
                    lengthY = self.__roofSlopeWidth
                    lengthX = self.roofLength
                else:
                    lengthX = self.roofLength
                    lengthY = self.__roofSlopeWidth
                fitP, currentX, currentY, lengthX, lengthY, deltaY, rotation =\
                    BirchPanel.FitPanel(page,lastX,lastY,lengthX,lengthY,deltaY,
                                        minX,minY, maxX,maxY)
                if not fitP:
                    return (True, -1, -1, deltaY)
                obj = techDoc.addObject("Part::Feature",self.name+"_Roof")
                obj.Shape = self.roofpanel
                obj.ViewObject.Visibility = False
                panel = techDoc.addObject('TechDraw::DrawViewPart',self.name+"_Roof_View")
                page.addView(panel)
                panel.Source = obj
                panel.X = currentX+lengthX/2
                panel.Y = currentY+lengthY/2
                panel.Rotation = rotation
                panel.Direction = self.roofnorm 
                lastX = currentX+lengthX+10
                lastY = currentY
                self.panelPage += 1
            else:
                # braces
                ibrace = self.panelPage - 2
                brace = self.braces[ibrace]
                bbox = brace.BoundBox
                lengthY = bbox.ZLength
                lengthX = max(bbox.XLength,bbox.YLength)
                fitP, currentX, currentY, lengthX, lengthY, deltaY, rotation =\
                    BirchPanel.FitPanel(page,lastX,lastY,lengthX,lengthY,deltaY,
                                        minX,minY, maxX,maxY)
                if not fitP:
                    return (True, -1, -1, deltaY)
                obj = techDoc.addObject("Part::Feature",self.name+"_Brace%03d"%(ibrace))
                obj.Shape = brace
                obj.ViewObject.Visibility = False
                panel = techDoc.addObject('TechDraw::DrawViewPart',self.name+"_Brace%03d_View"%(ibrace))
                page.addView(panel)
                panel.Source = obj
                panel.X = currentX+lengthX/2
                panel.Y = currentY+lengthY/2
                panel.Rotation = rotation
                panel.Direction = self.bracenorm
                lastX = currentX+lengthX+10
                lastY = currentY
                self.panelPage += 1
        return (True, lastX, lastY, deltaY)

class FlatRoof(BirchPanel, InstanceIter):
    def sortKey(self):
        bbox = self.roofPanel.BoundBox
        a = bbox.XLength
        b = bbox.YLength
        return math.hypot(a,b)
    def __str__(self):
        try:
            result = '<FlatRoof name="'+self.name+'"'
            result = result+'>'
            return result
        except BaseException:
            return "<FlatRoof>"
    def __init__(self,name,face):
        super(FlatRoof,self).__init__()
        self.name = name
        extrude = Base.Vector(0,0,BirchPanel.Thickness())
        self.roofPanel = face.extrude(extrude)
    @staticmethod
    def PolygonRoof(name,origin,poly):
        if not isinstance(origin,Base.Vector):
            raise RuntimeError("origin is not a Vector!")
        abspoly = list()
        for x,y in poly:
            abspoly.append(origin.add(Base.Vector(x,y,0)))
        return FlatRoof(name,Part.Face(Part.Wire(Part.makePolygon(abspoly))))
    @staticmethod
    def RectangleRoof(name,origin,width,height):
        if not isinstance(origin,Base.Vector):
            raise RuntimeError("origin is not a Vector!")
        return FlatRoof(name,Part.makePlane(width,height,origin,
                                            Base.Vector(0,0,1)))
    def show(self,doc=None):
        if doc==None:
            doc = App.activeDocument()
        obj = doc.addObject("Part::Feature",self.name)
        obj.Shape = self.roofPanel
        obj.Label=self.name
        obj.ViewObject.ShapeColor=self.Color
    def PanelPage(self,techDoc,page,lastX,lastY,deltaY,*,minX=50,minY=50,
                                             maxX=(24*25.4)-50,
                                             maxY=(16*25.4)-50):
        #print("*** FlatRoof.PanelPage(): page is ",page)
        #print("*** FlatRoof.PanelPage(): lastX = ",lastX,", lastY = ",lastY)
        bbox = self.roofPanel.BoundBox
        #print("*** FlatRoof.PanelPage(): bbox = ",bbox)
        lengthX = bbox.XLength
        lengthY = bbox.YLength
        fitP, currentX, currentY, lengthX, lengthY, deltaY, rotation =\
            BirchPanel.FitPanel(page,lastX,lastY,lengthX,lengthY,deltaY,
                                        minX,minY, maxX,maxY)
        if not fitP:
            return (True, -1, -1, deltaY)
        #print("*** FlatRoof.PanelPage(): currentX = ",currentX,", currentY = ",currentY)
        #print("*** FlatRoof.PanelPage(): lengthX = ",lengthX,", lengthY = ", lengthY)
        #print("*** FlatRoof.PanelPage(): rotation = ",rotation)
        obj = techDoc.addObject("Part::Feature",self.name)
        obj.Shape = self.roofPanel
        obj.ViewObject.Visibility = False
        panel = techDoc.addObject('TechDraw::DrawViewPart',self.name+"_View")
        page.addView(panel)
        panel.Source = obj
        panel.X = currentX+lengthX/2
        panel.Y = currentY+lengthY/2
        panel.Rotation = rotation
        panel.Direction = (0,0,1)
        return (True,currentX+lengthX+10,currentY,deltaY)

class AddamsFamilyHouse(BirchPanel):
    def PanelPage(self,techDoc,page,lastX,lastY,*,minX=50,minY=50,
                                             maxX=(24*25.4)-50,
                                             maxY=(16*25.4)-50):
        return (False, -1, -1)
    __leftWallOrigin = Base.Vector(0,0,0)
    __leftWidth = 162.43698120117188 - (-269.84454345703125)
    __leftWallWindows = [
                        Base.Vector(0,162.4369812011718-102.58531188964844,
                                    0.8360995054244995-(-18.670610427856445)),
                        Base.Vector(0,162.4369812011718-102.58531188964844,
                                    106.11219024658203-(-18.670610427856445)),
                        Base.Vector(0,162.4369812011718-36.285369873046875,
                                    0.8360995054244995-(-18.670610427856445)),
                        Base.Vector(0,162.4369812011718-36.285369873046875,
                                    106.11219024658203-(-18.670610427856445)),
                        Base.Vector(0,162.4369812011718-(-30.014583587646484),
                                    0.8360995054244995-(-18.670610427856445)),
                        Base.Vector(0,162.4369812011718-(-30.014583587646484),
                                    106.11219024658203-(-18.670610427856445)),
                        Base.Vector(0,162.4369812011718-(-100.25502014160156),
                                    0.8360995054244995-(-18.670610427856445)),
                        Base.Vector(0,162.4369812011718-(-100.25502014160156),
                                    106.11219024658203-(-18.670610427856445)),
                        Base.Vector(0,162.4369812011718-(-166.5549774169922),
                                    0.8360995054244995-(-18.670610427856445)),
                        Base.Vector(0,162.4369812011718-(-166.5549774169922),
                                    106.11219024658203-(-18.670610427856445)),
                        Base.Vector(0,162.4369812011718-(-232.8549041748047),
                                    0.8360995054244995-(-18.670610427856445)),
                        Base.Vector(0,162.4369812011718-(-232.8549041748047),
                                    106.11219024658203-(-18.670610427856445))
                        ]
    __leftProtrudeOrig = Base.Vector(0,0,0)
    __leftProtrudeWidth = (-213.16818237304688) - (-293.39385986328125)
    __wallHeight = 200.30540466308594-(-18.670610427856445)
    __leftProtrudeWindows = [Base.Vector(-263.86346435546875-(-293.39385986328125),0,
                                          0.8360995054244995-(-18.670610427856445)),
                             Base.Vector(-263.86346435546875-(-293.39385986328125),0,
                                          106.11219024658203-(-18.670610427856445))]
    __protrudeOffsetWidth = (162.4363250732422-115.00755310058594)+BirchPanel.Thickness()
    __mainWallWidth = (156.03421020507812-(-213.4210205078125))+BirchPanel.Thickness()
    __mainWallWindows=[Base.Vector(-171.88763427734375-(-213.4210205078125)+BirchPanel.Thickness(),0,
                                   0.8360995054244995-(-18.670610427856445)),
                       Base.Vector(-171.88763427734375-(-213.4210205078125)+BirchPanel.Thickness(),0,
                                    106.11219024658203-(-18.670610427856445)),
                       Base.Vector(-96.6558609008789-(-213.4210205078125)+BirchPanel.Thickness(),0,
                                   0.8360995054244995-(-18.670610427856445)),
                       Base.Vector(-96.6558609008789-(-213.4210205078125)+BirchPanel.Thickness(),0,
                                    106.11219024658203-(-18.670610427856445)),
                       Base.Vector(71.09040832519531-(-213.4210205078125)+BirchPanel.Thickness(),0,
                                    106.11219024658203-(-18.670610427856445)),
                       Base.Vector(101.06707763671875-(-213.4210205078125)+BirchPanel.Thickness(),0,
                                    106.11219024658203-(-18.670610427856445))
                      ]
    __entrywayXOffset = -48.76459503173828 - (-213.4203643798828) + 1
    __towerX = -39.011409759521484 - (-291.44384765625)
    __towerY = 0
    __towerZ = 88.55018615722656 - (-18.670610427856445)
    __towerOffsetWidth = 162.4363250732422 - 115.00755310058594
    __towerAdditionalPanelZ = 200.30540466308594 - (-18.670610427856445)
    __towerAdditionalPanelH =  307.5553894042969 - 200.30540466308594
    __towerAdditionalPanelWidth = 115.00755310058594 - 49.40283966064453
    __towerHeight = 307.5553894042969 - 88.55018615722656
    __towerWidth = 38.98531723022461 - (-39.011409759521484)
    __towerWindows = [
                      Base.Vector(-11.444066047668457-(-39.011409759521484),0,
                                  106.11219024658203-88.55018615722656),
                      Base.Vector(-14.261521339416504-(-39.011409759521484),0,
                                  211.02186584472656-88.55018615722656)
                     ]
    __bayX = 58.494903564453125 - (-291.44384765625)
    __bayY = 162.4363250732422 - 138.721923828125
    __bayZ =  -10.871750831604004 - (-18.670610427856445)
    __bayOffsetWidth = 138.721923828125 - 115.00755310058594
    __bayHeight = 72.95903778076172 - (-18.670610427856445)
    __bayWidth = 136.52464294433594 - 58.494903564453125
    __bayWindows = [
                    Base.Vector(71.09040832519531 - 58.494903564453125,0,
                                0.8360995054244995 - (-18.670610427856445)),
                    Base.Vector(101.06707763671875 - 58.494903564453125,0,
                                0.8360995054244995 - (-18.670610427856445))
                    ]
    __rightWallOrigin = Base.Vector(((-213.16818237304688) - (-293.39385986328125))+
                                    (156.03421020507812-(-213.4210205078125)) -
                                    BirchPanel.Thickness(),
                                    (162.4363250732422-115.00755310058594),0)
    __rightWidth1 = 115.00755310058594 - (-97.62701416015625)
    __rightProtrusionOWidth = 214.53517150878906 - 156.03421020507812
    __rightProtrusionWidth = -97.63031005859375 - (-222.4488067626953)
    __rightProtrusionWindows = [
                       Base.Vector(0,-97.63031005859375-(-133.61407470703125),
                                   0.8360995054244995-(-18.670610427856445)),
                       Base.Vector(0,-97.63031005859375-(-133.61407470703125),
                                   106.11219024658203-(-18.670610427856445)),
                       Base.Vector(0,-97.63031005859375-(-163.59075927734375),
                                   0.8360995054244995-(-18.670610427856445)),
                       Base.Vector(0,-97.63031005859375-(-163.59075927734375),
                                   106.11219024658203-(-18.670610427856445))
                               ]
    __rightWidth2 = (-222.4488067626953 - (-269.84454345703125)) +\
                    BirchPanel.Thickness()
    __greenhouseOrigin = Base.Vector(156.03402709960938-(-293.39385986328125),
                                     162.4369812011718-89.00996398925781,
                                     0)
    # Roof Overhang points
    # Vector (-291.2991943359375, 191.2957000732422, 162.26939392089844)
    # Vector (-291.44384765625, 200.30540466308594, 162.4363250732422)
    # Vector (-322.970458984375, 200.30540466308594, 202.69088745117188)
    # Vector (-291.44384765625, 200.30540466308594, -269.8438415527344)
    # Vector (-173.72952270507812, 197.5101318359375, 202.69088745117188)
    # Vector (-173.72952270507812, 197.5101318359375, 156.0223846435547)
    
    __roofOverhangXOffset = 40
    __roofOverhangYOffset = 40
    __rootOverhangZOffset = 200.30540466308594 - -18.670610427856445
    __leftRoofLength = 202.69088745117188 - -269.8438415527344
    __leftProtrudeFrontRoofLength = -173.72952270507812 - -322.970458984375
    __leftProtrudeRightRoofLength = 202.69088745117188-156.0223846435547+94.06
    __mainFrontWallRoofLength2 = 449.68-330.44 + RoofSection.OverhangOffset
    __MainRoofLevel = 296.97
    __MainRoofPolyXY1 = [ (18.39, 432.53), (18.39, 18.39), (49.51, 18.59),
                         (49.51, 78.13), (252.37, 78.13), (252.37, 432.93),
                         (18.39, 432.53)]
    __MainRoofPolyXY2 = [ (252.37, 113.03),
                         (330.52, 113.03), (330.52, 78.13), (418.93, 78.13),
                         (418.93, 290.82), (477.43, 290.82), (477.43, 354.13),
                         (418.93, 354.13), (418.93, 432.93), (252.37, 432.53),
                         (252.37, 113.03) ]
    __TowerLowerOverhangPolyXY = [ (252.43, 19.54), (252.43, 0.0), (330.43, 0),
                                   (330.43, 19.54), (358.32, 19.54), 
                                   (358.32, -27.89), (224.54, -27.89),
                                   (224.54, 19.54), (252.43, 19.54) ]
    __TowerRoofX = 270.36
    __TowerRoofY = 17.86
    __TowerRoofLevel = 404.225
    __TowerRoofW = 42.04
    __TowerRoofH = 77.19
    __BayRoofSTL = os.path.join(os.path.dirname(__file__),"BayRoof.stl")
    # Vector (-54.478546142578125, -76.32823181152344, -115.55367279052734)
    __BayRoofTranslateOrig = Base.Vector (-54.478546142578125, 
                                          -76.32823181152344, 
                                          -115.55367279052734)
    __BayRoofOrigin = Base.Vector(349.94-((434.75-427.97)/2),
                                  47.19,99.43)
    __BayRoofColor = (0.8, 0.8, 0.8)
    def __init__(self,name,origin):
        self.name = name
        if not isinstance(origin,Base.Vector):
            raise RuntimeError("origin is not a Vector!")
        self.origin = origin
        self.leftWall     = WallPanel(name + "_LeftWall",
                              self.origin.add(self.__leftWallOrigin),
                              self.__leftWidth,
                              self.__wallHeight,
                              windows=self.__leftWallWindows,
                              side='Left') 
        self.leftProtrude = WallPanel(name + "_LeftProtrude",
                             self.origin.add(self.__leftProtrudeOrig),
                             self.__leftProtrudeWidth, 
                             self.__wallHeight,
                             windows=self.__leftProtrudeWindows)
        self.leftProtrude.CutZYfingers(endz=self.__wallHeight)
        self.leftWall.Cut(self.leftProtrude)
        self.leftProtrude.CutZYfingers(
                    xoffset=self.__leftProtrudeWidth-BirchPanel.Thickness(),
                    endz=self.__wallHeight)
        protrudeOffsetOrigin = self.origin.add(
                    self.__leftProtrudeOrig.add(Base.Vector(
                                        self.__leftProtrudeWidth-BirchPanel.Thickness(),0,0)))
        self.protrudeOffset = WallPanel(name + "_ProtrudeOffset",
                                        protrudeOffsetOrigin,
                                        self.__protrudeOffsetWidth,
                                        self.__wallHeight,
                                        side='Right')
        self.protrudeOffset.Cut(self.leftProtrude)
        mainWallOrigin = protrudeOffsetOrigin.add(Base.Vector(0,(self.__protrudeOffsetWidth-BirchPanel.Thickness()),0))
        self.mainWall = WallPanel(name + "_MainWall",
                                  mainWallOrigin,
                                  self.__mainWallWidth,
                                  self.__wallHeight,
                                  windows=self.__mainWallWindows)
        self.mainWall.CutZYfingers(endz=self.__wallHeight)
        self.protrudeOffset.Cut(self.mainWall)
        self.mainWall.CutZYfingers(xoffset=self.__mainWallWidth-BirchPanel.Thickness(),
                                   endz=self.__wallHeight)
        entrywayOrigin = mainWallOrigin.add(Base.Vector(self.__entrywayXOffset,
                                                        0,0))
        self.entryway = EntryWayAndDoor(name + "_EntryWay",
                                        entrywayOrigin)
        self.mainWall.wall = self.entryway.CutDoorTunnelFromPanel(self.mainWall.wall)
        towerOffsetOrigin = self.origin.add(
                    Base.Vector(self.__towerX,
                                self.__towerY,
                                self.__towerZ))
        #print("*** FrontWall (constructor): towerOffsetOrigin is %s"%(towerOffsetOrigin))
        #print("*** FrontWall (constructor): self.__towerOffsetWidth is %f"%(self.__towerOffsetWidth))
        self.towerLeftOffset = WallPanel(name + "_TowerLeftOffset",
                                         towerOffsetOrigin,
                                         self.__towerOffsetWidth +
                                         BirchPanel.Thickness(),
                                         self.__towerHeight,
                                         side='Left')
        self.towerLeftOffset.CutZYfingers(endz=self.__towerHeight)
        self.towerLeftOffset.CutZYfingers(yoffset=self.__towerOffsetWidth,
                                          endz=self.__towerHeight-
                                                self.__towerAdditionalPanelH,
                                          startz=-BirchPanel.Thickness())
        self.towerLeftOffset.AddPanel(
            yoffset=self.__towerAdditionalPanelWidth+
                    self.__towerOffsetWidth,
            zoffset=self.__towerAdditionalPanelZ-towerOffsetOrigin.z,
            width=self.__towerAdditionalPanelWidth-
                    BirchPanel.Thickness(),
            height=self.__towerAdditionalPanelH)
        self.towerLeftOffset.CutZYfingers(
                    yoffset=(self.__towerAdditionalPanelWidth+
                                self.__towerOffsetWidth-
                                BirchPanel.Thickness()),
                    startz=self.__towerAdditionalPanelZ-
                            towerOffsetOrigin.z,
                    endz=self.__towerHeight)
        self.mainWall.Cut(self.towerLeftOffset)
        self.mainWall.CutPanel(xoffset=(towerOffsetOrigin.x-mainWallOrigin.x)+
                                       BirchPanel.Thickness(),
                               zoffset=self.__towerZ,
                               width=self.__towerWidth-(BirchPanel.Thickness()*2),
                               height=self.__towerHeight)
        towerFrontOrigin = self.origin.add(
                Base.Vector(self.__towerX,
                            self.__towerY,
                            self.__towerZ))
        self.tower = WallPanel(name + "_Tower",
                               towerFrontOrigin,
                               self.__towerWidth,
                               self.__towerHeight,
                               windows=self.__towerWindows,
                               side='Front')
        self.tower.Cut(self.towerLeftOffset)
        towerOffsetOrigin = self.origin.add(
                    Base.Vector(self.__towerX+self.__towerWidth-BirchPanel.Thickness(),
                                self.__towerY,
                                self.__towerZ))
        #print("*** FrontWall (constructor): towerOffsetOrigin is %s"%(towerOffsetOrigin))
        #print("*** FrontWall (constructor): self.__towerOffsetWidth is %f"%(self.__towerOffsetWidth))
        self.towerRightOffset = WallPanel(name + "_TowerRightOffset",
                                         towerOffsetOrigin,
                                         self.__towerOffsetWidth +
                                         BirchPanel.Thickness(),
                                         self.__towerHeight,
                                         side='Right')
        self.towerRightOffset.CutZYfingers(endz=self.__towerHeight)
        self.towerRightOffset.CutZYfingers(yoffset=self.__towerOffsetWidth,
                                          endz=self.__towerHeight-
                                                self.__towerAdditionalPanelH,
                                          startz=-BirchPanel.Thickness())
        self.tower.Cut(self.towerRightOffset)
        self.towerRightOffset.AddPanel(
            yoffset=self.__towerAdditionalPanelWidth+
                    self.__towerOffsetWidth,
            zoffset=self.__towerAdditionalPanelZ-towerOffsetOrigin.z,
            width=self.__towerAdditionalPanelWidth-
                    BirchPanel.Thickness(),
            height=self.__towerAdditionalPanelH)
        self.towerRightOffset.CutZYfingers(
                        yoffset=(self.__towerAdditionalPanelWidth+
                                 self.__towerOffsetWidth-
                                 BirchPanel.Thickness()),
                        startz=self.__towerAdditionalPanelZ-
                                towerOffsetOrigin.z,
                        endz=self.__towerHeight)
        self.mainWall.Cut(self.towerRightOffset)
        self.towerBack = WallPanel(
                name + "_TowerBack",
                towerFrontOrigin.add(
                    Base.Vector(0,
                                self.__towerOffsetWidth+
                                    self.__towerAdditionalPanelWidth-
                                    BirchPanel.Thickness(),
                                self.__towerAdditionalPanelZ-
                                    self.__towerAdditionalPanelH)),
                self.__towerWidth,
                self.__towerAdditionalPanelH)
        self.towerBack.Cut(self.towerRightOffset)
        self.towerBack.Cut(self.towerLeftOffset)
        bayOffsetOrigin = self.origin.add(
                    Base.Vector(self.__bayX,
                                self.__bayY,
                                self.__bayZ))
        self.bayLeftOffset = WallPanel(name + "_BayLeftOffset",
                                       bayOffsetOrigin,
                                       self.__bayOffsetWidth + 
                                        BirchPanel.Thickness(),
                                       self.__bayHeight,
                                       side='Left')
        self.bayLeftOffset.CutZYfingers(endz=self.__bayHeight)
        self.bayLeftOffset.CutZYfingers(yoffset=self.__bayOffsetWidth,
                                        endz=self.__bayHeight)
        self.bayLeftOffset.CutYZfingers(endy=self.__bayOffsetWidth)
        self.mainWall.Cut(self.bayLeftOffset)
        xoff1 = (bayOffsetOrigin.x-mainWallOrigin.x)+BirchPanel.Thickness()
        cutwidth = self.__bayWidth-(BirchPanel.Thickness()*2)
        xoff2 = xoff1+cutwidth
        self.mainWall.CutPanel(xoffset=xoff1,
                               zoffset=self.__bayZ+BirchPanel.Thickness(),
                               width=cutwidth,
                               height=self.__bayHeight-BirchPanel.Thickness())

        self.mainWall.CutXZfingers(zoffset=self.__bayZ,
                                   startx=xoff1,
                                   endx=xoff2)

        bayFrontOrigin = self.origin.add(
                            Base.Vector(self.__bayX,self.__bayY,self.__bayZ))
        self.bay = WallPanel(name + "_Bay",
                             bayFrontOrigin,
                             self.__bayWidth,
                             self.__bayHeight,
                             windows=self.__bayWindows,
                             side='Front')
        self.bay.Cut(self.bayLeftOffset)
        self.bay.CutXZfingers(endx=self.__bayWidth)
        bayOffsetOrigin = self.origin.add(
                            Base.Vector(self.__bayX+self.__bayWidth-
                                            BirchPanel.Thickness(),
                                        self.__bayY,self.__bayZ))
        self.bayRightOffset = WallPanel(name + "_BayRightOffset",
                                        bayOffsetOrigin,
                                        self.__bayOffsetWidth + BirchPanel.Thickness(),
                                        self.__bayHeight,
                                        side='Right')
        self.bayRightOffset.CutZYfingers(endz=self.__bayHeight)
        self.bayRightOffset.CutZYfingers(yoffset=self.__bayOffsetWidth,
                                         endz=self.__bayHeight)
        self.bay.Cut(self.bayRightOffset)
        self.mainWall.Cut(self.bayRightOffset)
        self.bayRightOffset.CutYZfingers(endy=self.__bayOffsetWidth)
        self.bayFloor = Floor(name + "_BayFloor",
                              bayFrontOrigin,
                              self.__bayOffsetWidth+BirchPanel.Thickness(),
                              self.__bayWidth)
        self.bayFloor.Cut(self.mainWall)
        self.bayFloor.Cut(self.bayRightOffset)
        self.bayFloor.Cut(self.bayLeftOffset)
        self.bayFloor.Cut(self.bay)
        self.rightWall1    = WallPanel(name + "_RightWall1",
                                       self.origin.add(self.__rightWallOrigin),
                                       self.__rightWidth1+BirchPanel.Thickness(),
                                       self.__wallHeight,
                                       side='Right')
        self.rightWall1.Cut(self.mainWall)
        self.rightWall1.CutZYfingers(endz=self.__wallHeight,
                                    yoffset=self.__rightWidth1)
        rightWallProtrusionOrigin = self.__rightWallOrigin.add(
                    Base.Vector(0,self.__rightWidth1,0))
        self.rightWallProtrusionLO = WallPanel(name + "_RightWallProtrusionLO",
                                             self.origin.add(rightWallProtrusionOrigin),
                                             self.__rightProtrusionOWidth+
                                                BirchPanel.Thickness(),
                                             self.__wallHeight,
                                             side='Front')
        self.rightWallProtrusionLO.Cut(self.rightWall1)
        self.rightWallProtrusion = WallPanel(name + "_RightWallProtrusion",
                                             rightWallProtrusionOrigin.add(
                                               Base.Vector(
                                                self.__rightProtrusionOWidth,
                                                0,0)),
                                             self.__rightProtrusionWidth,
                                             self.__wallHeight,
                                             windows=self.__rightProtrusionWindows,
                                             side='Right')
        self.rightWallProtrusion.CutZYfingers(endz=self.__wallHeight)
        self.rightWallProtrusion.CutZYfingers(endz=self.__wallHeight,
                                              yoffset=self.__rightProtrusionWidth-BirchPanel.Thickness())
        self.rightWallProtrusionLO.Cut(self.rightWallProtrusion)
        self.rightWallProtrusionRO = WallPanel(name + "_RightWallProtrusionRO",
                                               rightWallProtrusionOrigin.add(
                                                Base.Vector(self.__rightProtrusionOWidth+
                                                BirchPanel.Thickness(),
                                                self.__rightProtrusionWidth,
                                                0)),
                                               self.__rightProtrusionOWidth+
                                                BirchPanel.Thickness(),
                                               self.__wallHeight,
                                               side='Rear')
        self.rightWallProtrusionRO.Cut(self.rightWallProtrusion)
        self.rightWall2    = WallPanel(name + "_RightWall2",
                                       self.origin.add(
                                        self.__rightWallOrigin).add(
                                            Base.Vector(0,
                                            self.__rightWidth1-
                                            BirchPanel.Thickness()+
                                            self.__rightProtrusionWidth,0)),
                                       self.__rightWidth2,
                                       self.__wallHeight,
                                       side='Right')
        self.rightWall2.CutZYfingers(endz=self.__wallHeight)
        self.rightWallProtrusionRO.Cut(self.rightWall2)
        self.greenhouse = GreenHouse(name+"_Greenhouse",
                                     origin.add(self.__greenhouseOrigin))
        leftroofOrigin = self.origin.add(
                Base.Vector(-self.__roofOverhangXOffset,
                            -self.__roofOverhangYOffset,
                            self.__rootOverhangZOffset))
        self.leftRoof = RoofSection(name+"_LeftRoof",
                                    leftroofOrigin,
                                    self.__leftRoofLength,
                                    side='Left',
                                    braces=[100,200,300,400],
                                    start='OuterMiter')
        self.leftProtrudeFrontRoof = \
            RoofSection(name+"_LeftProtrudeFrontRoof",
                        leftroofOrigin.add(Base.Vector(-1.17,0.0)),
                        self.__leftProtrudeFrontRoofLength,
                        side='Front',
                        braces=[self.__leftProtrudeFrontRoofLength/2],
                        start='OuterMiter',end='OuterMiter')
        self.leftProtrudeRightRoof = \
            RoofSection(name+"_LeftProtrudeRightRoof",
                        leftroofOrigin.add(
                            Base.Vector(self.__leftProtrudeFrontRoofLength-
                                        81.17,
                                        -1.17,0)),
                        self.__leftProtrudeRightRoofLength,
                        braces=[self.__leftProtrudeRightRoofLength*.65],
                        side='Right',
                        start='OuterMiter',end='InnerMiter')
        self.leftProtrudeRightRoof.overhang = \
            self.leftProtrudeRightRoof.overhang.cut(
                self.leftRoof.overhang)
        mainFrontWallRoofOrigin1 = mainWallOrigin.add(
                            Base.Vector(-self.__roofOverhangXOffset-
                                        BirchPanel.Thickness()*3+.55,
                                        -self.__roofOverhangYOffset+
                                        BirchPanel.Thickness()*4-.56,
                                        self.__rootOverhangZOffset))
        mainFrontWallRoofLength1 = towerOffsetOrigin.x- \
                        mainFrontWallRoofOrigin1.x - \
                        self.__towerWidth + \
                        BirchPanel.Thickness()
        self.mainFrontWallRoof1 = \
            RoofSection(name+"_MainFrontWallRoof1",
                        mainFrontWallRoofOrigin1,
                        mainFrontWallRoofLength1,
                        side='Front',
                        braces=[100,200,mainFrontWallRoofLength1-
                                        BirchPanel.Thickness()],
                        start='InnerMiter')
        self.mainFrontWallRoof1.overhang = \
            self.mainFrontWallRoof1.overhang.cut(
                self.leftRoof.overhang)
        mainFrontWallRoofOrigin2 = mainFrontWallRoofOrigin1.add(
                Base.Vector(mainFrontWallRoofLength1+self.__towerWidth,0,0))
        self.mainFrontWallRoof2 = \
            RoofSection(name+"_MainFrontWallRoof2",
                        mainFrontWallRoofOrigin2,
                        self.__mainFrontWallRoofLength2,
                        side='Front',
                        braces=[0,65],
                        end='OuterMiter')
        rightWallRoofOrigin1 = mainFrontWallRoofOrigin2.add(
                Base.Vector(self.__mainFrontWallRoofLength2-80,-1.17,0))
        rightWallRoofLength1 = self.__rightWidth1+81.21
        self.rightWallRoof1 = \
            RoofSection(name+"_RightWallRoof1",
                        rightWallRoofOrigin1,
                        rightWallRoofLength1,
                        side='Right',
                        braces=[100,200],
                        start='OuterMiter',
                        end='InnerMiter')
        rightWallProtrusionRoofOrigin = rightWallRoofOrigin1.add(
            Base.Vector(0,rightWallRoofLength1-80,0))
        rightWallProtrusionRoofLength = self.__rightProtrusionOWidth+80
        self.rightWallProtrusionLORoof = \
            RoofSection(name+"_RightWallProtrusionLORoof",
                        rightWallProtrusionRoofOrigin,
                        rightWallProtrusionRoofLength,
                        braces=[rightWallProtrusionRoofLength/2],
                        side='Front',
                        start='InnerMiter',end='OuterMiter')
        rightWallProtrusionRoofOrigin = rightWallProtrusionRoofOrigin.add(
            Base.Vector(rightWallProtrusionRoofLength-80,-1.14,0))
        rightWallProtrusionRoofLength = self.__rightProtrusionWidth+56.77
        self.rightWallProtrusionRoof = \
            RoofSection(name+"_RightWallProtrusionRoof",
                        rightWallProtrusionRoofOrigin,
                        rightWallProtrusionRoofLength,
                        braces=[rightWallProtrusionRoofLength/2],
                        side='Right',
                        start='OuterMiter',end='OuterMiter')
        rightWallProtrusionRoofOrigin = rightWallProtrusionRoofOrigin.add(
            Base.Vector(-58.5,rightWallProtrusionRoofLength-80,0))
        rightWallProtrusionRoofLength = self.__rightProtrusionOWidth+80
        self.rightWallProtrusionRORoof = \
            RoofSection(name+"_RightWallProtrusionRORoof",
                        rightWallProtrusionRoofOrigin,
                        rightWallProtrusionRoofLength,
                        braces=[rightWallProtrusionRoofLength/2],
                        side='Rear',
                        end='OuterMiter', start='InnerMiter')
        rightWall2RoofLength = self.__rightWidth2+49.2
        self.rightWall2Roof = RoofSection(name+"_RightWall2Roof",
                                          rightWallProtrusionRoofOrigin,
                                          rightWall2RoofLength,
                                          braces=[rightWall2RoofLength/2],
                                          side='Right',
                                          start='InnerMiter')
        towerLeftOffsetRoofOrigin = self.origin.add(
            Base.Vector(291.97-80,#self.__towerX-self.__roofOverhangXOffset-1.015,
                        self.__towerY-self.__roofOverhangYOffset-.53,
                        self.__towerZ+self.__towerHeight))
        #print("*** towerLeftOffsetRoofOrigin = ",towerLeftOffsetRoofOrigin)
        towerLeftOffsetRoofLength = \
            self.__towerAdditionalPanelWidth+self.__towerOffsetWidth+ \
            self.__roofOverhangYOffset*2 + 1
        #print("*** towerLeftOffsetRoofLength = ",towerLeftOffsetRoofLength)
        self.towerLeftOffsetRoof = RoofSection(name+"_TowerLeftOffsetRoof",
                                               towerLeftOffsetRoofOrigin,
                                               towerLeftOffsetRoofLength,
                                               side='Left',
                                               braces=[towerLeftOffsetRoofLength*.5],
                                               start='OuterMiter',
                                               end='OuterMiter')
        towerFrontRoofLength = self.__towerWidth+self.__roofOverhangYOffset*2+\
                    2.09
        self.towerFrontRoof = RoofSection(name+"_TowerFrontRoof",
                                          towerLeftOffsetRoofOrigin.add(
                                            Base.Vector(-1.1699999999999875,
                                                        0,0)),
                                          towerFrontRoofLength,
                                          side='Front',
                                          braces=[towerFrontRoofLength/2],
                                          start='OuterMiter',
                                          end='OuterMiter')
        towerRightOffsetRoofOrigin = towerLeftOffsetRoofOrigin.add(
            Base.Vector(79,-1.17,0))
        #print("*** towerRightOffsetRoofOrigin = ",towerRightOffsetRoofOrigin)
        self.towerRightOffsetRoof = RoofSection(name+"_TowerRightOffsetRoof",
                                                 towerRightOffsetRoofOrigin,
                                                 towerLeftOffsetRoofLength+2.23,
                                                 side='Right',
                                                 braces=[towerLeftOffsetRoofLength*.55],
                                                 start='OuterMiter',
                                                 end='OuterMiter')
        towerRearRoofOrigin = towerRightOffsetRoofOrigin.add(
            Base.Vector(-80.16,towerLeftOffsetRoofLength-78.83,0))
        self.towerRearRoof = RoofSection(name+"_TowerRearRoof",
                                         towerRearRoofOrigin,
                                         towerFrontRoofLength-1,
                                         side='Rear',
                                         braces=[towerFrontRoofLength/2],
                                         start='OuterMiter',
                                         end='OuterMiter')
        self.mainRoofPanel1 = FlatRoof.PolygonRoof(name+"_MainRoofPanel1",
                                         origin.add(
                                            Base.Vector(0,0,
                                                        self.__MainRoofLevel)),
                                         self.__MainRoofPolyXY1)
        self.mainRoofPanel2 = FlatRoof.PolygonRoof(name+"_MainRoofPanel2",
                                         origin.add(
                                            Base.Vector(0,0,
                                                        self.__MainRoofLevel)),
                                         self.__MainRoofPolyXY2)
        self.towerOverHang = FlatRoof.PolygonRoof(name+"_TowerOverHang",
                                                  origin.add(
                                                    Base.Vector(0,0,
                                                                self.__rootOverhangZOffset)),
                                          self.__TowerLowerOverhangPolyXY)
        self.towerRoofPanel = FlatRoof.RectangleRoof(name+"_TowerRoofPanel",
                                            origin.add(
                                                Base.Vector(self.__TowerRoofX,
                                                            self.__TowerRoofY,
                                                            self.__TowerRoofLevel)),
                                                            self.__TowerRoofW,
                                                            self.__TowerRoofH)
        bayroof = Mesh.read(self.__BayRoofSTL)
        bayroof.translate(self.__BayRoofTranslateOrig.x,
                          self.__BayRoofTranslateOrig.y,
                          self.__BayRoofTranslateOrig.z)
        bayroof.rotate(math.pi/2,0,0)
        ro = self.origin.add(self.__BayRoofOrigin)
        bayroof.translate(ro.x,ro.y,ro.z) 
        self.bayroof = bayroof
    def show(self,doc=None):
        if doc==None:
            doc = App.activeDocument()
        self.leftWall.show(doc)
        self.leftProtrude.show(doc)
        self.protrudeOffset.show(doc)
        self.mainWall.show(doc)
        self.entryway.show(doc)
        self.towerLeftOffset.show(doc)
        self.tower.show(doc)
        self.towerRightOffset.show(doc)
        self.towerBack.show(doc)
        self.bayLeftOffset.show(doc)
        self.bay.show(doc)
        self.bayRightOffset.show(doc)
        self.bayFloor.show(doc)
        self.rightWall1.show(doc)
        self.rightWallProtrusionLO.show(doc)
        self.rightWallProtrusion.show(doc)
        self.rightWallProtrusionRO.show(doc)
        self.rightWall2.show(doc)
        self.greenhouse.show(doc)
        self.leftRoof.show(doc)
        self.leftProtrudeFrontRoof.show(doc)
        self.leftProtrudeRightRoof.show(doc)
        self.mainFrontWallRoof1.show(doc)
        self.mainFrontWallRoof2.show(doc)
        self.rightWallRoof1.show(doc)
        self.rightWallProtrusionLORoof.show(doc)
        self.rightWallProtrusionRoof.show(doc)
        self.rightWallProtrusionRORoof.show(doc)
        self.rightWall2Roof.show(doc)
        self.towerLeftOffsetRoof.show(doc)
        self.towerFrontRoof.show(doc)
        self.towerRightOffsetRoof.show(doc)
        self.towerRearRoof.show(doc)
        self.mainRoofPanel1.show(doc)
        self.mainRoofPanel2.show(doc)
        self.towerOverHang.show(doc)
        self.towerRoofPanel.show(doc)
        obj = doc.addObject("Mesh::Feature",self.name+"_BayRoof")
        obj.Mesh = self.bayroof
        obj.Label=self.name+"_BayRoof"
        obj.ViewObject.ShapeColor=self.__BayRoofColor

Pages = list()
def NewPage(techdoc,pagenum=0):
    pagenum += 1
    page = techdoc.addObject('TechDraw::DrawPage','SmallCutPanelPage_%03d'%(pagenum))
    page.Template = techdoc.SmallCutPanelTemplate
    page.ViewObject.show()
    Pages.append((page, pagenum))
    return (page, pagenum)
    

if __name__ == '__main__':
    if "AddamsFamilyHouse" in App.listDocuments().keys():
        App.closeDocument("AddamsFamilyHouse")
    doc = App.newDocument("AddamsFamilyHouse")
    AddamsFamilyHouse = AddamsFamilyHouse("AddamsFamilyHouse",Base.Vector(0,0,0))
    AddamsFamilyHouse.show(doc)
    Gui.activeDocument().activeView().viewTop()
    Gui.SendMsgToActiveView("ViewFit")
    #LargeArchWindow.Trim3DPrint()
    #LargeArchWindow.LEDMount3DPrint()
    if "AddamsFamilyHouse_BirchPanels" in App.listDocuments().keys():
        App.closeDocument("AddamsFamilyHouse_BirchPanels")
    techdoc = App.newDocument("AddamsFamilyHouse_BirchPanels")
    techdoc.addObject('TechDraw::DrawSVGTemplate','SmallCutPanelTemplate')
    techdoc.SmallCutPanelTemplate.Template = os.path.join(
                        os.path.dirname(__file__),"smallcutpanel.svg")
    page, pagenum = NewPage(techdoc)
    pages = list()
    lastX = 50
    lastY = 50
    deltaY = 0
    for roof in RoofSection.SortedList():
        for i in range(2):
            #print("*** RoofSection loop: ",i,": roof is ",roof)
            #print("*** RoofSection loop: pagenum is ",pagenum)
            hasPanel, newX, newY, deltaY = roof.PanelPage(techdoc,
                                                          page,
                                                          lastX,lastY,deltaY)
            #print("*** RoofSection loop: hasPanel, newX, newY, deltaY",hasPanel, newX, newY, deltaY)
            if not hasPanel:
                break
            if newX < 0 and newY < 0:
                # need new page
                page, pagenum = NewPage(techdoc,pagenum)
                lastX = 50
                lastY = 50
                deltaY = 0
            else:
                lastX = newX
                lastY = newY
                break
    for floor in Floor.SortedList():
        for i in range(2):
            #print("*** Floor loop: ",i,": floor is ",floor)
            #print("*** Floor loop: pagenum is ",pagenum)
            hasPanel, newX, newY, deltaY = floor.PanelPage(techdoc,
                                                      page,
                                                      lastX,lastY,deltaY)
            #print("*** Floor loop: hasPanel, newX, newY, deltaY",hasPanel, newX, newY, deltaY)
            if not hasPanel:
                break
            if newX < 0 and newY < 0:
                # need new page
                page, pagenum = NewPage(techdoc,pagenum)
                lastX = 50
                lastY = 50
                deltaY = 0
            else:
                lastX = newX
                lastY = newY
                break
    for wall in WallPanel.SortedList():
        for i in range(2):
            #print("*** WallPanel loop: ",i,": wall is ",wall)
            #print("*** WallPanel loop: pagenum is ",pagenum)
            hasPanel, newX, newY, deltaY = wall.PanelPage(techdoc,
                                                          page,
                                                          lastX,lastY,deltaY)
            #print("*** WallPanel loop: hasPanel, newX, newY, deltaY",hasPanel, newX, newY, deltaY)
            if not hasPanel:
                break
            if newX < 0 and newY < 0:
                # need new page
                page, pagenum = NewPage(techdoc,pagenum)
                lastX = 50
                lastY = 50
                deltaY = 0
            else:
                lastX = newX
                lastY = newY
                break
    for roof in FlatRoof.SortedList():
        for i in range(2):
            #print("*** FlatRoof loop: ",i,": roof is ",roof)
            #print("*** FlatRoof loop: pagenum is ",pagenum)
            hasPanel, newX, newY, deltaY = roof.PanelPage(techdoc,
                                                          page,
                                                          lastX,lastY,deltaY)
            #print("*** FlatRoof loop: hasPanel, newX, newY, deltaY",hasPanel, newX, newY, deltaY)
            if not hasPanel:
                break
            if newX < 0 and newY < 0:
                # need new page
                page, pagenum = NewPage(techdoc,pagenum)
                lastX = 50
                lastY = 50
                deltaY = 0
            else:
                lastX = newX
                lastY = newY
                break
    techdoc.recompute()
    sleep(500)
    for page,number in Pages:
        TechDrawGui.exportPageAsSvg(page,
                     os.path.join(os.path.dirname(__file__),
                                  "AddamsFamilyHouse_Panel%03d.svg"%(number)))
