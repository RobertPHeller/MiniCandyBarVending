#*****************************************************************************
#
#  System        : 
#  Module        : 
#  Object Name   : $RCSfile$
#  Revision      : $Revision$
#  Date          : $Date$
#  Author        : $Author$
#  Created By    : Robert Heller
#  Created       : Mon Jun 2 15:01:05 2025
#  Last Modified : <250605.1431>
#
#  Description	
#
#  Notes
#
#  History
#	
#*****************************************************************************
#
#    Copyright (C) 2025  Robert Heller D/B/A Deepwoods Software
#			51 Locke Hill Road
#			Wendell, MA 01379-9728
#
#    This program is free software; you can redistribute it and/or modify
#    it under the terms of the GNU General Public License as published by
#    the Free Software Foundation; either version 2 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program; if not, write to the Free Software
#    Foundation, Inc., 675 Mass Ave, Cambridge, MA 02139, USA.
#
# 
#
#*****************************************************************************


import FreeCAD as App
import Part, TechDraw, Mesh, MeshPart, TechDrawGui
from FreeCAD import Base

import os
import sys
sys.path.append(os.path.dirname(__file__))
import time
from PySide.QtCore import QCoreApplication, QEventLoop, QTimer

def execute(loop, ms):
    timer = QTimer()
    timer.setSingleShot(True)
    
    timer.timeout.connect(loop.quit)
    timer.start(ms)
    loop.exec_()

def sleep(ms):
    if not QCoreApplication.instance():
        app = QCoreApplication([])
        execute(app, ms)
    else:
        loop = QEventLoop()
        execute(loop, ms)

from collections import defaultdict

def EidthBucket(x):
    return round(x / 3.5)*3.5

def mesh2solid(mesh):
    segments = mesh.getPlanarSegments(.99 )
    print("*** mesh2solid(): len(segments) is ",len(segments) )
    faces = []

    for i in segments:
        print("*** mesh2solid() [for i in segments]: len(i) is ",len(i))
        if len(i) > 0:
            # a segment can have inner holes
            wires = MeshPart.wireFromSegment(mesh, i)
            print("*** mesh2solid() [for i in segments]: len(wires) is ",len(wires) )
            # we assume that the exterior boundary is that one with the biggest bounding box
            if len(wires) > 0:
                ext = None
                max_length=0
                for i in wires:
                    print("*** mesh2solid() [for i in wires]: i is ",i)
                    if i.BoundBox.DiagonalLength > max_length:
                        max_length = i.BoundBox.DiagonalLength
                        ext = i
                print("*** mesh2solid() [after for i in wires]: ext = ",ext)
                wires.remove(ext)
                # all interior wires mark a hole and must reverse their orientation, otherwise Part.Face fails
                for i in wires:
                    i.reverse()
                
                # make sure that the exterior wires comes as first in the list
                wires.insert(0, ext)
                print("*** mesh2solid() [About to call Part.Face(wires)]: ",len(wires))
                try:
                    faces.append(Part.Face(wires))
                except Part.OCCError as e:
                    pass
    print("*** mesh2solid(): len(faces) is ",len(faces))
    if len(faces) == 0:
        return None
    solid = Part.Solid(Part.Shell(faces))
    return(solid)

def mesh2YPlanes(points,triangles,namebase,newdoc,solid=True):
    Yplanes = defaultdict(list)
    ys = set()
    for t in triangles:
        for tp in t:
            p = points[tp]
            #print("*** p is ",p)
            yb = EidthBucket(p.y)
            Yplanes[yb].append(t)
            #print("*** planes[",yb,"] = ",Yplanes[yb])
            ys.add(yb)
            #print("*** ys is ",ys)
    ylist = list()
    for y in ys:
        ylist.append(y)
    ylist.sort()
    for iy,y in enumerate(ylist):
        #print("*** iy = ",iy,", y = ",y)
        meshtriangles = list()
        for t in Yplanes[y]:
            tri = list()
            for tp in t:
                point = points[tp]
                yb = EidthBucket(point.y)
                #print("*** yb = ",yb,", point.y = ",point.y)
                if yb == y:
                    tri.append(point)
            if len(tri) == 3:
                for tp  in tri:
                    meshtriangles.append(tp)
        if len(meshtriangles) > 0:
            #print("*** len(meshtriangles) is ",len(meshtriangles))
            mesh = Mesh.Mesh(meshtriangles)
            #print("*** mesh is ",mesh)
            name = "%sYRoof%d"%(namebase,iy)
            #print("*** name is ",name)
            #shape = Part.Shape()
            #shape.makeShapeFromMesh(mesh.Topology, 3.5) 
            #solidpart = Part.makeSolid(shape)
            if solid:
                solidpart = mesh2solid(mesh)
                if solidpart != None:
                    obj = newdoc.addObject("Part::Feature",name)
                    #print("*** obj is ",obj)
                    obj.Shape = solidpart
                    obj.Label=name
                    obj.ViewObject.ShapeColor=tuple([0.5,0.5,0.5])
            else:
                obj = newdoc.addObject("Mesh::Feature",name)
                obj.Mesh = mesh
                obj.Label=name
                obj.ViewObject.ShapeColor=tuple([0.5,0.5,0.5])
            
def minmaxZ(triangles):
    minZ = None
    maxZ = None
    for p in triangles:
        if minZ == None:
            minZ = p.z
        if maxZ == None:
            maxZ = p.z
        if p.z < minZ:
            minZ = p.z
        if p.z > maxZ:
            maxZ = p.z
    return (minZ,maxZ)

def mesh2ZXPlanes(points,triangles,namebase,newdoc,solid=True):
    Zplanes = defaultdict(list)
    zs = set()
    for t in triangles:
        for tp in t:
            p = points[tp]
            #print("*** p is ",p)
            zb = EidthBucket(p.z)
            Zplanes[zb].append(t)
            #print("*** planes[",zb,"] = ",Zplanes[zb])
            zs.add(zb)
            #print("*** zs is ",zs)
    zlist = list()
    for z in zs:
        zlist.append(z)
    zlist.sort()
    for iz,z in enumerate(zlist):
        #print("*** iz = ",iz,", z = ",z)
        meshtriangles = list()
        for t in Zplanes[z]:
            tri = list()
            for tp in t:
                point = points[tp]
                zb = EidthBucket(point.z)
                #print("*** zb = ",zb,", point.z = ",point.z)
                if zb == z:
                    tri.append(point)
            if len(tri) == 3:
                for tp  in tri:
                    meshtriangles.append(tp)
        if len(meshtriangles) > 0:
            print("*** len(meshtriangles) is ",len(meshtriangles))
            print("*** meshtriangles is ",meshtriangles)
            minZ,maxZ = minmaxZ(meshtriangles)
            print("*** minZ = ",minZ,", maxZ = ",maxZ,", range is ",maxZ-minZ)
            
            mesh = Mesh.Mesh(meshtriangles)
            print("*** mesh is ",mesh)
            name = "%sZWall%d"%(namebase,iz)
            print("*** name is ",name)
            #shape = Part.Shape()
            #shape.makeShapeFromMesh(mesh.Topology, 3.5) 
            #solidpart = Part.makeSolid(shape)
            if solid:
                solidpart = mesh2solid(mesh)
                if solidpart != None:
                    obj = newdoc.addObject("Part::Feature",name)
                    #print("*** obj is ",obj)
                    obj.Shape = solidpart
                    obj.Label=name
                    obj.ViewObject.ShapeColor=tuple([0.5,0.5,0.5])
            else:
                obj = newdoc.addObject("Mesh::Feature",name)
                obj.Mesh = mesh
                obj.Label=name
                obj.ViewObject.ShapeColor=tuple([0.5,0.5,0.5])
    Xplanes = defaultdict(list)
    xs = set()
    for t in triangles:
        for tp in t:
            p = points[tp]
            #print("*** p is ",p)
            xb = EidthBucket(p.x)
            Xplanes[xb].append(t)
            #print("*** planes[",xb,"] = ",Zplanes[xb])
            xs.add(xb)
            #print("*** xs is ",xs)
    xlist = list()
    for x in xs:
        xlist.append(x)
    xlist.sort()
    for ix,x in enumerate(xlist):
        #print("*** ix = ",ix,", x = ",x)
        meshtriangles = list()
        for t in Xplanes[x]:
            tri = list()
            for tp in t:
                point = points[tp]
                xb = EidthBucket(point.x)
                #print("*** xb = ",xb,", point.x = ",point.x)
                if xb == x:
                    tri.append(point)
            if len(tri) == 3:
                for tp  in tri:
                    meshtriangles.append(tp)
        if len(meshtriangles) > 0:
            #print("*** len(meshtriangles) is ",len(meshtriangles))
            mesh = Mesh.Mesh(meshtriangles)
            #print("*** mesh is ",mesh)
            name = "%sXWall%d"%(namebase,ix)
            #print("*** name is ",name)
            #shape = Part.Shape()
            #shape.makeShapeFromMesh(mesh.Topology, 3.5) 
            #solidpart = Part.makeSolid(shape)
            if solid:
                solidpart = mesh2solid(mesh)
                if solidpart != None:
                    obj = newdoc.addObject("Part::Feature",name)
                    #print("*** obj is ",obj)
                    obj.Shape = solidpart
                    obj.Label=name
                    obj.ViewObject.ShapeColor=tuple([0.5,0.5,0.5])
            else:
                obj = newdoc.addObject("Mesh::Feature",name)
                obj.Mesh = mesh
                obj.Label=name
                obj.ViewObject.ShapeColor=tuple([0.5,0.5,0.5])

if __name__ == '__main__':
    doc = None
    newdoc = None
    for docname in App.listDocuments():
        lddoc = App.getDocument(docname)
        if lddoc.Label == 'addams_family_house_planarmeshes':
            doc = lddoc
        if lddoc.Label == 'addams_family_house_planes':
            newdoc = lddoc            
    if doc == None:
        App.open("addams_family_house_planarmeshes.FCStd")
        doc = App.getDocument("addams_family_house_planarmeshes")
    if newdoc == None:
        newdoc = App.newDocument("addams_family_house_panels")
    App.ActiveDocument=newdoc

    # X and Z Panels (Walls)
    #house = doc.Sketchfab_Scene_Sketchfab_model_root_GLTF_SceneRootNode_House_0_Object_4
    #houseMesh = house.Mesh
    #topo = houseMesh.Topology
    #points, triangles = topo
    #mesh2ZXPlanes(points,triangles,"House_0_Object_4",newdoc,False)
    #house = doc.Sketchfab_Scene_Sketchfab_model_root_GLTF_SceneRootNode_House_0_Object_5
    #houseMesh = house.Mesh
    #topo = houseMesh.Topology
    #points, triangles = topo
    #mesh2ZXPlanes(points,triangles,"House_0_Object_5",newdoc,False)
    #triangleroof = doc.Sketchfab_Scene_Sketchfab_model_root_GLTF_SceneRootNode_Triangle_roof_6_Object_17
    #triangleroofMesh = triangleroof.Mesh
    #topo = triangleroofMesh.Topology
    #points, triangles = topo
    #mesh2ZXPlanes(points,triangles,"Triangle_roof_6_Object_17",newdoc,False)
    #greenhouse = doc.Sketchfab_Scene_Sketchfab_model_root_GLTF_SceneRootNode_Greenhouse_7_Object_21
    #greenhouseMesh = greenhouse.Mesh
    #topo = greenhouseMesh.Topology
    #points, triangles = topo
    #mesh2ZXPlanes(points,triangles,"Greenhouse_7_Object_21",newdoc,False)
    #greenhouse = doc.Sketchfab_Scene_Sketchfab_model_root_GLTF_SceneRootNode_Greenhouse_7_Object_23
    #greenhouseMesh = greenhouse.Mesh
    #topo = greenhouseMesh.Topology
    #points, triangles = topo
    #mesh2ZXPlanes(points,triangles,"Greenhouse_7_Object_23",newdoc,False)
    #dormers = doc.Sketchfab_Scene_Sketchfab_model_root_GLTF_SceneRootNode_Roof_windows_21_Object_54
    #dormersMesh = dormers.Mesh
    #topo = dormersMesh.Topology
    #points, triangles = topo
    #mesh2ZXPlanes(points,triangles,"Roof_windows_21_Object_54",newdoc,False)
    # Y panels (Roofs and Overhangs)
    #overhang = doc.Sketchfab_Scene_Sketchfab_model_root_GLTF_SceneRootNode_Overhang_supports_3_Object_11
    #overhangMesh = overhang.Mesh
    #topo = overhangMesh.Topology
    #points, triangles = topo
    #mesh2YPlanes(points,triangles,"Overhang_supports_3_Object_11",newdoc,False)
    #frontoverhang = doc.Sketchfab_Scene_Sketchfab_model_root_GLTF_SceneRootNode_Front_overhang_roof_4_Object_13
    #frontoverhangMesh = frontoverhang.Mesh
    #topo = frontoverhangMesh.Topology
    #points, triangles = topo
    #mesh2YPlanes(points,triangles,"Front_overhang_roof_4_Object_13",newdoc,False)
    #greenhouseRoof = doc.Sketchfab_Scene_Sketchfab_model_root_GLTF_SceneRootNode_Greenhouse_roof_5_Object_15
    #greenhouseRoofMesh = greenhouseRoof.Mesh
    #topo = greenhouseRoofMesh.Topology
    #points, triangles = topo
    #mesh2YPlanes(points,triangles,"Greenhouse_roof_5_Object_15",newdoc,False)
    #joinedRoof = doc.Sketchfab_Scene_Sketchfab_model_root_GLTF_SceneRootNode_Joined_roof_2_Object_9
    #joinedRoofMesh = joinedRoof.Mesh
    #topo = joinedRoofMesh.Topology
    #points, triangles = topo
    #mesh2YPlanes(points,triangles,"Joined_roof_2_Object_9",newdoc,False)
    #tower = doc.Sketchfab_Scene_Sketchfab_model_root_GLTF_SceneRootNode_Tower_roof_1_Object_7
    #towerMesh = tower.Mesh
    #topo = towerMesh.Topology
    #points, triangles = topo
    #mesh2YPlanes(points,triangles,"Tower_roof_1_Object_7",newdoc,False)

    solidpart = mesh2solid(doc.House_0_Object_4ZWall57.Mesh)
    if solidpart != None:
        obj = newdoc.addObject("Part::Feature",'House_0_Object_4ZWall57')
        obj.Shape = solidpart
        obj.Label='House_0_Object_4ZWall57'
        obj.ViewObject.ShapeColor=tuple([0.5,0.5,0.5])
   
    #House_0_Object_4ZWall62
    #House_0_Object_4ZWall63
    #House_0_Object_5ZWall9
    #House_0_Object_5ZWall8
    #House_0_Object_5ZWall7
    
    
    Gui.SendMsgToActiveView("ViewFit")
    
    # insert a Page object and assign a template
    #newdoc.addObject('TechDraw::DrawSVGTemplate','SmallCutPanelTemplate') 
    #newdoc.SmallCutPanelTemplate.Template = "smallcutpanel.svg" 
    #newdoc.addObject('TechDraw::DrawPage','SmallCutPanelPage_1')
    #newdoc.SmallCutPanelPage_1.Template = newdoc.SmallCutPanelTemplate
    #newdoc.SmallCutPanelPage_1.ViewObject.show()
    
    # Panels (1/8" hardwood laser cut plywood):
    # Front walls:
    # House_0_Object_4ZWall57 -- Main
    # House_0_Object_4ZWall62 -- Right protrusion
    # House_0_Object_4ZWall63 -- Left protrusion and tower
    # House_0_Object_5ZWall7  -- Main foundation
    # House_0_Object_5ZWall8  -- Right protrusion foundation
    # House_0_Object_5ZWall9  -- Left protrusion foundation
    # Left Walls
    # Right Walls
    # Roofs and Overhanges
    # Triangle_roof_6_Object_17ZWall1
    # Triangle_roof_6_Object_17ZWall2
    # Greenhouse_7_Object_21ZWall34
    # Roof_windows_21_Object_54ZWall18
    # Roof_windows_21_Object_54ZWall17
    # Roof_windows_21_Object_54ZWall16
    # Overhang_supports_3_Object_11YRoof6
    # Overhang_supports_3_Object_11YRoof8
    # Front_overhang_roof_4_Object_13YRoof0
    # Front_overhang_roof_4_Object_13YRoof1
    # Front_overhang_roof_4_Object_13YRoof5
    # Greenhouse_roof_5_Object_15YRoof0
    # Greenhouse_roof_5_Object_15YRoof7
    # Joined_roof_2_Object_9YRoof0
    # Joined_roof_2_Object_9YRoof11
    # Tower_roof_1_Object_7YRoof0
    # Tower_roof_1_Object_7YRoof9

    #frontMain = newdoc.House_0_Object_4ZWall57
    #front_main = newdoc.addObject('TechDraw::DrawViewPart','Front Main')
    #newdoc.SmallCutPanelPage_1.addView(front_main)
    #front_main.Source = frontMain
    #front_main.X = 190
    #front_main.Y = 150
    #front_main.Rotation = 0
    #front_main.Direction = (0,0,1)
    
    #newdoc.recompute()
